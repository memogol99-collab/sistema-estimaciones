;;; =====================================================================
;;;  MEMO_Cargador.lsp  -  MEMO SISTEMA 2.1.1
;;;  ARCHIVO GENERADO: no editar a mano; edite herramientas/catalogo.py
;;;
;;;  Un solo cargador para todos los LISP. NO carga los 55 archivos al
;;;  abrir cada dibujo: define cada comando como "stub" y el archivo real
;;;  se carga la primera vez que se usa el comando (carga bajo demanda).
;;;  Si existen versiones compiladas (MEMO_COMPILAR) de esta misma versión,
;;;  carga los .fas en lugar de los .lsp.
;;; =====================================================================
(vl-load-com)

(if (not memo:cargado)
  (progn
    (setq memo:version "2.1.1")
    (setq memo:raiz (findfile "MEMO_Cargador.lsp"))
    (if memo:raiz
      (setq memo:raiz (vl-string-translate "\\" "/" (vl-filename-directory memo:raiz))))
    (setq memo:archivos-cargados nil memo:num-comandos 0 memo:*mapa* nil memo:*stubs* nil memo:*ya-definidos* nil)
    (setq memo:dir-fas (strcat (vl-string-translate "\\" "/" (getenv "APPDATA")) "/MEMO_SISTEMA/FAS/"))

    ;; Valores configurables: (CLAVE "defecto" "descripción" "NUM|TXT" "opciones")
    (setq memo:*cfg-def* '(
      ("TABLA_PORTAPAPELES" "PREGUNTAR" "Tablas: usar portapapeles (SI/NO/PREGUNTAR)" "TXT" "SI,NO,PREGUNTAR")
      ("COP_ANCHO_NO" "0.5" "COP: ancho columna No." "NUM" "")
      ("COP_ANCHO_CODIGO" "4.6641" "COP: ancho No.+Código" "NUM" "")
      ("COP_ANCHO_CONCEPTO" "21.1083" "COP: ancho Concepto" "NUM" "")
      ("COP_ANCHO_UNIDAD" "2.0596" "COP: ancho Unidad" "NUM" "")
      ("COP_ANCHO_PRECIO" "2.0596" "COP: ancho Precio" "NUM" "")
      ("ASI_ANCHO_NO" "0.9841" "ASI: ancho No." "NUM" "")
      ("ASI_ANCHO_CODIGO" "1.7887" "ASI: ancho Código" "NUM" "")
      ("ASI_ANCHO_DESCRIPCION" "14.8620" "ASI: ancho Descripción" "NUM" "")
      ("ASI_ANCHO_UNIDAD" "1.1700" "ASI: ancho Unidad" "NUM" "")
      ("ASI_ANCHO_PU" "1.7250" "ASI: ancho P.U." "NUM" "")
      ("ASI_ANCHO_CANTIDAD" "1.6997" "ASI: ancho Cantidad" "NUM" "")
      ("ASI_ANCHO_IMPORTE" "1.9849" "ASI: ancho Importe" "NUM" "")
      ("CSSA_ANCHO_TOTAL" "24.0964" "CSSA: ancho total de la tabla" "NUM" "")
      ("BACHEO_ESPESOR" "0.10" "Bacheo: espesor para volumen en EXR (m)" "NUM" "")
      ("TABLA_ULTIMO" "Obras" "MTABLA: último formato usado" "TXT" "")
      ("AREA_ULTIMO" "Prefijo" "MAREA: última opción usada" "TXT" "")
    ))

    ;; ¿Hay FAS compilados para ESTA versión?
    (defun memo:fas-vigente-p (/ f v)
      (if (and (setq f (findfile (strcat memo:dir-fas "version.txt")))
               (setq f (open f "r")))
        (progn (setq v (read-line f)) (close f) (= v memo:version))))
    (setq memo:usar-fas (memo:fas-vigente-p))

    ;; Ruta real a cargar (.fas compilado o .lsp)
    (defun memo:ruta (rel / fas)
      (setq fas (strcat memo:dir-fas (vl-filename-base rel) ".fas"))
      (if (and memo:usar-fas (findfile fas))
        fas
        (strcat memo:raiz "/LISP/" rel ".lsp")))

    ;; Carga el archivo real y ejecuta el comando solicitado
    (defun memo:cargar (rel cmd / ruta res)
      (setq ruta (memo:ruta rel))
      (cond
        ((member rel memo:archivos-cargados)
         (princ (strcat "\nMEMO: " rel " se cargó pero no define el comando " cmd)))
        ((not (findfile ruta))
         (princ (strcat "\nMEMO: no se encuentra " ruta)))
        (T
         (setq memo:archivos-cargados (cons rel memo:archivos-cargados))
         (setq res (vl-catch-all-apply 'load (list ruta)))
         (if (vl-catch-all-error-p res)
           (princ (strcat "\nMEMO: error al cargar " rel ": " (vl-catch-all-error-message res)))
           (eval (list (read (strcat "C:" cmd)))))))
      (princ))

    ;; Define los comandos de un archivo como stubs que lo cargan al primer uso
    (defun memo:al (rel cmds / sym)
      (setq memo:*mapa* (cons (list rel cmds) memo:*mapa*))
      (foreach cmd cmds
        (setq sym (read (strcat "C:" cmd)))
        ;; Si otro LISP cargado antes ya definía el comando, se reemplaza por
        ;; la versión MEMO (la que esperan los botones) y se avisa.
        (if (eval sym) (setq memo:*ya-definidos* (cons cmd memo:*ya-definidos*)))
        (eval (list 'defun sym nil (list 'memo:cargar rel cmd)))
        (setq memo:*stubs* (cons (cons cmd (vl-princ-to-string (eval sym))) memo:*stubs*))
        (setq memo:num-comandos (1+ memo:num-comandos))))

    ;; T si el comando todavía es el stub (su archivo no lo definió)
    (defun memo:es-stub-p (cmd / s)
      (and (setq s (assoc cmd memo:*stubs*))
           (= (cdr s) (vl-princ-to-string (eval (read (strcat "C:" cmd)))))))

    (if memo:raiz
      (progn
        ;; Biblioteca común (siempre)
        (if (vl-catch-all-error-p (vl-catch-all-apply 'load (list (memo:ruta "Sistema/MEMO_Lib"))))
          (princ "\nMEMO: no se pudo cargar la biblioteca MEMO_Lib."))
        (memo:al "Estimaciones/COP_ConceptosObrasPublicas" '("COP" "LIMPIARTABLA"))
        (memo:al "Estimaciones/ASI_ConceptosAsipona" '("ASI"))
        (memo:al "Estimaciones/CSSA_ConceptosSSA" '("LIMPIARCSSA" "CSSA"))
        (memo:al "Estimaciones/LC_LimpiarConceptos" '("LCO"))
        (memo:al "Estimaciones/CAS_CompAreaSecc" '("CAS" "QA"))
        (memo:al "Estimaciones/IJPG_CadAJpg" '("IJPG" "IJPG-EMF" "IJPG-PC3"))
        (memo:al "Bacheo/RS_RectanguloSnap" '("RS" "RSC" "AEC" "RC2" "RSHATCH" "RS-CONFIG"))
        (memo:al "Bacheo/RV_RenumerarRectangulos" '("RENUMERARVECINO" "RNB"))
        (memo:al "Bacheo/COTB_CotarBaches" '("COTB"))
        (memo:al "Bacheo/EXR_ExportaRectangulos" '("EXR" "VERLISTA" "VERXDATA" "AXD"))
        (memo:al "Bacheo/HR_HatchRectangulos" '("HR"))
        (memo:al "Bacheo/BTR_BorrarTextoEnRect" '("BTR"))
        (memo:al "Secciones/EL_Elevacion" '("ELTN"))
        (memo:al "Secciones/R00_CambiaNumeros" '("R00"))
        (memo:al "Secciones/AM2_AreaM2" '("AM2"))
        (memo:al "Secciones/HA_AreaPrefijo" '("HA2" "HA" "HAPREF" "HARESET" "HAINFO"))
        (memo:al "Secciones/AS_AreaSecc3P" '("AS"))
        (memo:al "Secciones/AC_AreaContorno" '("AC"))
        (memo:al "Secciones/AH_AreaHatch" '("AH2" "AH" "AHINFO"))
        (memo:al "Secciones/EA_ExportarEstArea" '("EA" "HAEA-EXPORT" "EA-HA" "HAEA"))
        (memo:al "Textos/CT_Toolbox" '("CTB" "CTE" "CTP" "IPT" "CTN" "STV"))
        (memo:al "Textos/CTT_CambiaTexto" '("CTX"))
        (memo:al "Textos/ALIT_AlinearTexto" '("ALIT"))
        (memo:al "Textos/PTE_Pendiente" '("PTE"))
        (memo:al "Textos/UL_MayMin" '("UL"))
        (memo:al "Textos/PS_PrefijoSufijo" '("PS" "PREFSUFIND" "VERPREFSUF" "LIMPIARPREFSUF" "SETPREFSUF"))
        (memo:al "Textos/RTT_RotarTexto" '("RTT"))
        (memo:al "Textos/ST_SumaTextos" '("ST" "ST-TEST"))
        (memo:al "Textos/CTAF_TextoAltoAncho" '("CTAF" "CTF" "CTAF2"))
        (memo:al "Textos/CORM_CoordenadasATexto" '("COR" "COR2" "CORM"))
        (memo:al "Hatch/SPH_SeparaFusionaHatch" '("SEPARAHATCH" "SPH" "FUSIONHATCH" "FH"))
        (memo:al "Hatch/CHS_HatchSimilar" '("CHS"))
        (memo:al "VistasLayout/CV_CrearVistas" '("CV"))
        (memo:al "VistasLayout/AV_GuardarRestaurarVistas" '("AV" "GV"))
        (memo:al "VistasLayout/BV_BorrarVistas" '("BV"))
        (memo:al "VistasLayout/CL_ClonarLayout" '("CLO"))
        (memo:al "VistasLayout/CFTL_ConfigurarLayouts" '("CFTL"))
        (memo:al "VistasLayout/SL_SuprimirLayouts" '("SL"))
        (memo:al "Topografia/ICE_ImportarPuntos" '("ICE"))
        (memo:al "Topografia/PCC_PuntosCivilACapas" '("PCC"))
        (memo:al "Topografia/UPP_UnirPuntosPol" '("UPP" "UPPA"))
        (memo:al "Topografia/MP_MallaPuntos" '("MALLA-PUNTOS" "EXPORTAR-PUNTOS" "MLL" "EXP"))
        (memo:al "Topografia/XY_ExportarCoordPol" '("X-Y"))
        (memo:al "Topografia/CPEC_ColorearPorElevacion" '("CPEC"))
        (memo:al "Topografia/CCN_CurvasNivel" '("CCN" "CCNT" "CCNAYUDA" "CCNTEST"))
        (memo:al "Topografia/ECN_ElevacionCurvas" '("ECN-DUPLICADOS" "ECN-P" "ECN-M" "ECN-ETIQ" "ECN-ETIQM" "ECN-QUITAR" "ECN-RECOLOR" "ECN-LIMPIA" "ECN-DESHACER" "ECN-LISTA" "ECN-CONFIG" "ETM" "ECN"))
        (memo:al "Topografia/BPOL_BorraPol" '("BPOL"))
        (memo:al "Topografia/CLIPIT" '("CLIPIT"))
        (memo:al "Batimetria/XYZ_Tools" '("XYZRESTAURAR" "XYZAYUDA" "XYZLOTES" "XYZBORRAR" "XYZ" "IXYZ" "PZ" "XYZUNIR" "P-Z" "IZ" "OZ" "ZM" "XYZU" "EXYZ" "XYZEXPORTAR" "XYZTEST"))
        (memo:al "Batimetria/PIT_PuntoInsTexto" '("PIT"))
        (memo:al "Batimetria/PERFIL_Transversal" '("PERFIL"))
        (memo:al "Bloques/IBC_BloquesEnCapa" '("IBC"))
        (memo:al "Bloques/IBCZ_BloquesEnCapaEscala" '("IBCZ" "ARBOLES" "RAP" "DES" "IBPV" "IBTM" "CFE" "VERBLOQUES" "VERCAPAS" "CONFIGESCALAS"))
        (memo:al "Bloques/IBM_BloquesMultiples" '("IBM"))
        (memo:al "Sistema/MEMO_Unificados" '("MTABLA" "MAREA" "MBACHEO" "MEMO_CONFIG"))
        (setq memo:*mapa* (reverse memo:*mapa*))
        (if memo:*ya-definidos*
          (progn
            (princ "\nMEMO: otro LISP cargado antes ya definía estos comandos; se usa la versión MEMO:")
            (princ "\n      ")
            (foreach c (reverse memo:*ya-definidos*) (princ (strcat c " ")))
            (princ "\n      (revise APPLOAD > Conjunto de inicio y quite los LISP viejos)")))
        (setq memo:cargado T)
        (princ (strcat "\nMEMO SISTEMA " memo:version " listo: " (itoa memo:num-comandos)
                       " comandos" (if memo:usar-fas " (compilados)" "")
                       ". Escriba MEMO_AYUDA para ver la lista.")))
      (princ "\nMEMO: no se encontró MEMO_Cargador.lsp en las rutas de soporte."))))

;;; ---------------------------------------------------------------------
;;; Comandos propios del sistema
;;; ---------------------------------------------------------------------
(defun c:MEMO_AYUDA ()
  (textscr)
  (princ (strcat "\n========== MEMO SISTEMA " memo:version " =========="))
  (princ "\n\n### MEMO ESTIMACIONES")
  (princ "\n  -- Conceptos")
  (princ "\n   MTABLA           Tabla de conceptos desde el portapapeles: detecta el formato (5 col. Obras Públicas, 7 Asipona, 4 SSA) y llama a COP/ASI/CSSA.")
  (princ "\n   COP              Tabla de conceptos de 5 columnas (No. | Código | Concepto | Unidad | Precio). Lee lo copiado en Excel (portapapeles).")
  (princ "\n   ASI              Tabla de conceptos de 7 columnas (No. | Código | Descripción | Unidad | P.U. | Cantidad | Importe) con total. Lee el portapapeles.")
  (princ "\n   CSSA             Tabla de conceptos formato SSA (No. | Concepto | Unidad | Cantidad) con recuadros. Lee el portapapeles.")
  (princ "\n   LCO              Borra TEXT y MTEXT de la capa CONCEPTOS.")
  (princ "\n   LIMPIARTABLA     Borra textos de las capas CONCEPTOS y ENCABEZADOS (tablas COP/ASI).")
  (princ "\n   LIMPIARCSSA      Borra los elementos creados por CSSA.")
  (princ "\n  -- Bacheo")
  (princ "\n   MBACHEO          Bacheo paso a paso: Dibujar > Numerar > Cotar > Hatch > Exportar.")
  (princ "\n   RS               Dibuja rectángulos (baches) con cotas por fuera y hatch individual en capa Hatch_Bache.")
  (princ "\n   RNB              Renumera los rectángulos seleccionados por vecino más cercano.")
  (princ "\n   COTB             Anota largo y ancho de cada rectángulo en la capa GEOMETRIA_RECTANGULOS.")
  (princ "\n   EXR              Exporta los baches a CSV: número, largo, ancho, área, volumen y acumulado.")
  (princ "\n   HR               Aplica hatch a los rectángulos seleccionados.")
  (princ "\n   BTR              Borra los textos que quedan dentro de los rectángulos seleccionados.")
  (princ "\n   RSHATCH          Vuelve a aplicar el hatch a polilíneas existentes.")
  (princ "\n   RSC              Crea cotas con 2 decimales (estilo de RS).")
  (princ "\n   AEC              Actualiza el estilo de cota usado por RS.")
  (princ "\n   RC2              Redondea cotas existentes a 2 decimales.")
  (princ "\n   RS-CONFIG        Configura patrón, escala, ángulo, color y capa del hatch de RS.")
  (princ "\n   VERLISTA         Muestra la lista de rectángulos en memoria.")
  (princ "\n   AXD              Asigna XDATA (número, largo, ancho) a rectángulos existentes.")
  (princ "\n  -- Secciones")
  (princ "\n   ELTN             Coloca elevaciones de terreno natural en secciones (escala vertical 1:1000 o 1:100).")
  (princ "\n   CAS              Cálculo de áreas con fórmulas y valores (triángulos, trapecios, rectángulos, círculos).")
  (princ "\n   QA               Cálculo rápido de áreas con valores sustituidos.")
  (princ "\n   AS               Área de sección por 3 puntos (estilo text-Secc).")
  (princ "\n   R00              Cambia números de los textos por 00.00 (conserva 'M2').")
  (princ "\n  -- Áreas")
  (princ "\n   MAREA            Un solo comando para las áreas: Prefijo, Rápido, M2, Hatch, Contorno, 3 puntos, Detalle, Valores, Exportar.")
  (princ "\n   EA               Etiqueta áreas por capa y exporta a CSV/Excel (interfaz completa).")
  (princ "\n   HA2              Pone el área de un hatch en un texto, preguntando prefijo.")
  (princ "\n   HA               Pone el área de un hatch usando el último prefijo guardado.")
  (princ "\n   HAPREF           Cambia el prefijo usado por HA/HA2.")
  (princ "\n   HAINFO           Muestra la configuración actual de HA.")
  (princ "\n   AM2              Actualiza el área en m² de un hatch en su texto.")
  (princ "\n   AC               Calcula y actualiza áreas de secciones a partir de contornos.")
  (princ "\n   AH               Extrae el área de hatches: 'AREA DE [TIPO]=[VALOR]M2'.")
  (princ "\n   AH2              Versión completa de AH con opciones.")
  (princ "\n   HAEA-EXPORT      Sólo exporta las áreas a Excel/CSV.")
  (princ "\n   EA-HA            Etiquetado manual de EA (antes se llamaba HA y chocaba con el HA de prefijos).")
  (princ "\n  -- Imagen")
  (princ "\n   IJPG             Exporta el área seleccionada a imagen JPG/PNG con recorte exacto.")
  (princ "\n   IJPG-EMF         Exporta el área seleccionada a EMF vectorial sin bordes.")
  (princ "\n   IJPG-PC3         Configura el trazador PC3 para JPG/PNG.")
  (princ "\n\n### MEMO TOPOGRAFÍA")
  (princ "\n  -- Puntos")
  (princ "\n   ICE              Importa puntos desde TXT/CSV/XYZ con capas y etiquetas.")
  (princ "\n   PCC              Clasifica puntos y textos de CivilCAD en capas.")
  (princ "\n   MALLA-PUNTOS     Genera malla de puntos por IDW con coloreo y etiquetas.")
  (princ "\n   UPP              Une puntos con una polilínea.")
  (princ "\n   UPPA             UPP con referencia a objetos automática (nodo, punto medio, intersección).")
  (princ "\n   PIT              Convierte '-18 36' en '-18.36' y crea puntos en el punto de inserción.")
  (princ "\n   EXPORTAR-PUNTOS  Exporta puntos a CSV.")
  (princ "\n   X-Y              Exporta las coordenadas X Y de una polilínea a TXT.")
  (princ "\n   CPEC             Colorea puntos AutoCAD según su elevación.")
  (princ "\n  -- Curvas de nivel")
  (princ "\n   CCN              Colorea curvas de nivel existentes por intervalos (no modifica geometría).")
  (princ "\n   ECN              Asigna elevación a curvas de nivel y las etiqueta (menú principal).")
  (princ "\n   ECN-P            ECN: propagación de elevación por clic.")
  (princ "\n   ECN-M            ECN: método manual.")
  (princ "\n   ECN-ETIQ         ECN: etiquetas automáticas con intervalo.")
  (princ "\n   ECN-ETIQM        ECN: etiqueta manual con intervalo.")
  (princ "\n   ECN-RECOLOR      ECN: colorear por elevación.")
  (princ "\n   ECN-DUPLICADOS   ECN: limpia etiquetas duplicadas.")
  (princ "\n   ECN-CONFIG       ECN: configurar parámetros.")
  (princ "\n   ECN-DESHACER     ECN: deshace el último coloreo.")
  (princ "\n   ECN-LISTA        ECN: lista curvas por capa/elevación.")
  (princ "\n  -- Batimetría XYZ")
  (princ "\n   XYZ              Menú principal de XYZ-Tools (importar, procesar, unir, exportar).")
  (princ "\n   IXYZ             Importa archivos XYZ con simbología por profundidad.")
  (princ "\n   PZ               Procesa archivos XYZ (5 modos de procesamiento).")
  (princ "\n   P-Z              Herramientas de puntos (Procesa_Puntos).")
  (princ "\n   XYZU             Une varios archivos XYZ.")
  (princ "\n   EXYZ             Exporta puntos seleccionados a XYZ.")
  (princ "\n   IZ               Invierte el signo de Z de los puntos seleccionados.")
  (princ "\n   OZ               Suma una distancia a la Z de los puntos seleccionados.")
  (princ "\n   ZM               Muestra Z mínima y máxima de la selección.")
  (princ "\n   XYZLOTES         Lista los lotes importados.")
  (princ "\n   XYZBORRAR        Borra un lote importado.")
  (princ "\n   XYZAYUDA         Ayuda de XYZ-Tools.")
  (princ "\n  -- Perfiles")
  (princ "\n   PERFIL           Genera secciones transversales batimétricas con retícula y área.")
  (princ "\n  -- Edición")
  (princ "\n   BPOL             Borra/recorta objetos por un objeto cerrado.")
  (princ "\n   CLIPIT           Recorta imágenes con un rectángulo (polilínea cerrada).")
  (princ "\n  -- Bloques")
  (princ "\n   IBC              Inserta bloques en los puntos de capas *-Punto detectando la escala.")
  (princ "\n   IBCZ             Inserta bloques en capa con escalas definidas.")
  (princ "\n   IBM              Copia un bloque de referencia a múltiples puntos.")
  (princ "\n   ARBOLES          Inserta 'Arbol' (escala 760.32).")
  (princ "\n   RAP              Inserta 'RAP'.")
  (princ "\n   DES              Inserta 'Descarga'.")
  (princ "\n   IBPV             Inserta 'PV Existente'.")
  (princ "\n   IBTM             Inserta 'Poste de TM'.")
  (princ "\n   CFE              Inserta 'Poste de CFE'.")
  (princ "\n   VERBLOQUES       Muestra los bloques existentes en el dibujo.")
  (princ "\n   VERCAPAS         Muestra las capas finales requeridas.")
  (princ "\n   CONFIGESCALAS    Muestra las escalas configuradas.")
  (princ "\n\n### MEMO DIBUJO")
  (princ "\n  -- Textos")
  (princ "\n   CTB              Caja de herramientas de texto (diálogo con 6 herramientas).")
  (princ "\n   CTE              Copia texto con opción de estilo.")
  (princ "\n   CTP              Copia texto con propiedades (texto / todo / sólo rotación).")
  (princ "\n   IPT              Iguala propiedades de texto.")
  (princ "\n   CTN              Copia texto con numeración automática (V-1, V-2, V-3...).")
  (princ "\n   STV              Suma o resta un valor a textos numéricos.")
  (princ "\n   CTX              Cambia los textos seleccionados por un texto tecleado.")
  (princ "\n   ALIT             Alinea textos (TEXT/MTEXT) en vertical u horizontal.")
  (princ "\n   RTT              Rota textos sobre su punto medio.")
  (princ "\n   UL               Cambia entre mayúsculas y minúsculas.")
  (princ "\n   PS               Agrega prefijo y/o sufijo a varios textos.")
  (princ "\n   PREFSUFIND       Agrega prefijo/sufijo texto por texto.")
  (princ "\n   SETPREFSUF       Establece los valores por defecto de PS.")
  (princ "\n   ST               Suma los valores numéricos de los textos seleccionados.")
  (princ "\n   PTE              Rotula la pendiente entre dos puntos.")
  (princ "\n   CTAF             Cambia altura y factor de ancho de textos.")
  (princ "\n  -- Coordenadas")
  (princ "\n   CORM             Actualiza textos E/N/Z con las coordenadas de varios puntos.")
  (princ "\n   COR              Actualiza textos con coordenadas (decimales y prefijo).")
  (princ "\n   COR2             Coordenadas rápido (3 decimales, con prefijo).")
  (princ "\n  -- Hatch")
  (princ "\n   FH               Fusiona varios hatches en uno solo con el patrón de referencia.")
  (princ "\n   SPH              Separa un hatch compuesto en un hatch por frontera.")
  (princ "\n   CHS              Crea un hatch con las propiedades de otro.")
  (princ "\n  -- Vistas")
  (princ "\n   CV               Crea vistas en capa VISTAS a partir de puntos.")
  (princ "\n   GV               Guarda la vista actual con número o nombre.")
  (princ "\n   AV               Restaura una vista guardada.")
  (princ "\n   BV               Lista y borra vistas guardadas.")
  (princ "\n  -- Layouts")
  (princ "\n   CLO              Copia el layout activo N veces con prefijo.")
  (princ "\n   CFTL             Configura página de varios layouts a la vez (copiar de uno existente).")
  (princ "\n   SL               Elimina layouts seleccionados de una lista.")
  (princ "\n  -- MEMO")
  (princ "\n   MEMO_AYUDA       Lista todos los comandos del MEMO SISTEMA por categoría.")
  (princ "\n   MEMO_CONFIG      Anchos de tablas, espesor de bacheo, uso del portapapeles, etc.")
  (princ "\n   MEMO_INFO        Muestra versión, carpeta y archivos cargados del MEMO SISTEMA.")
  (princ "\n   MEMO_VERIFICAR   Carga todos los archivos y comprueba que cada comando exista (usar en un dibujo nuevo).")
  (princ "\n   MEMO_COMPILAR    Compila los LISP a FAS en %APPDATA%\\MEMO_SISTEMA\\FAS para cargar más rápido.")
  (princ "\n   MEMO_QUITAR_ANTERIOR Descarga el menú anterior 'MEMO' (Memo.cuix) para que no se duplique.")
  (princ "\n\nComandos renombrados por chocar con tu acad.pgp:")
  (princ "\n   EL    -> ELTN                   (tu alias ELIPSE)")
  (princ "\n   RV    -> RNB                    (tu alias REVOLUCION)")
  (princ "\n   CC    -> RSC                    (tu alias CERRARCINTA)")
  (princ "\n   PV    -> IBPV                   (tu alias PTOVISTA)")
  (princ "\n   TM    -> IBTM                   (tu alias TILEMODE)")
  (princ "\n   CL    -> CLO                    (tu alias LINEACENTRO)")
  (princ "\n   LC    -> LCO                    (tu alias LINEACENTRO)")
  (princ "\n   CT    -> CTB                    (tu alias TXTC / CTABLESTYLE)")
  (princ "\n   CTT   -> CTX                    (tu alias ADMATRB)")
  (princ "\n   MP    -> (eliminado; use MLL)   (tu alias EMPALME)")
  (princ "\n\nTip: pase el cursor sobre los botones de las fichas MEMO para ver la descripción.")
  (princ))

(defun c:MEMO_INFO ()
  (princ (strcat "\nMEMO SISTEMA " memo:version))
  (princ (strcat "\nCarpeta: " (if memo:raiz memo:raiz "(no encontrada)")))
  (princ (strcat "\nComandos registrados: " (itoa memo:num-comandos)))
  (if memo:*ya-definidos*
    (progn
      (princ "\nYa los definía otro LISP (ahora usan la versión MEMO):")
      (foreach c (reverse memo:*ya-definidos*) (princ (strcat " " c)))))
  (princ (strcat "\nCompilados (FAS): " (if memo:usar-fas (strcat "SÍ, en " memo:dir-fas) "no (se usan los .lsp)")))
  (princ (strcat "\nBiblioteca MEMO_Lib: " (if memo:portapapeles "cargada" "NO cargada")))
  (princ "\nArchivos ya cargados en este dibujo:")
  (if memo:archivos-cargados
    (foreach a (reverse memo:archivos-cargados) (princ (strcat "\n  " a)))
    (princ "\n  (ninguno todavía: se cargan al usar cada comando)"))
  (princ (strcat "\nMenú MEMO_SISTEMA: " (if (menugroup "MEMO_SISTEMA") "cargado" "NO cargado")))
  (princ))

(defun c:MEMO_QUITAR_ANTERIOR (/ old)
  ;; Descarga el menú viejo 'MEMO' (Memo.cuix con rutas fijas a AutoCAD 2024/2026)
  (if (menugroup "MEMO")
    (progn
      (setq old (getvar "CMDECHO"))
      (setvar "CMDECHO" 0)
      (command "_.CUIUNLOAD" "MEMO")
      (setvar "CMDECHO" old)
      (princ "\nMenú anterior MEMO descargado. Sus LISP ya no se cargarán al abrir dibujos."))
    (princ "\nEl menú anterior MEMO no está cargado. Nada que hacer."))
  (princ))

;;; Carga TODOS los archivos y comprueba que cada comando quede definido.
(defun c:MEMO_VERIFICAR (/ ok n res err faltan)
  (princ "\nMEMO_VERIFICAR carga TODOS los archivos en este dibujo")
  (princ "\n(algunos crean estilos o capas al cargarse): úselo en un dibujo nuevo.")
  (initget "Si No")
  (if (/= (getkword "\n¿Continuar? [Si/No] <Si>: ") "No")
    (progn
      (setq ok 0 n 0)
      (foreach par memo:*mapa*
        (setq res nil)
        (if (not (member (car par) memo:archivos-cargados))
          (progn
            (setq res (vl-catch-all-apply 'load (list (memo:ruta (car par)))))
            (setq memo:archivos-cargados (cons (car par) memo:archivos-cargados))))
        (if (vl-catch-all-error-p res)
          (setq err (cons (strcat (car par) " -> " (vl-catch-all-error-message res)) err))
          (foreach c (cadr par)
            (setq n (1+ n))
            (if (memo:es-stub-p c)
              (setq faltan (cons (strcat c "  (" (car par) ")") faltan))
              (setq ok (1+ ok))))))
      (textscr)
      (princ "\n\n=========== RESULTADO MEMO_VERIFICAR ===========")
      (princ (strcat "\nArchivos: " (itoa (length memo:*mapa*))
                     "    Comandos correctos: " (itoa ok) " de " (itoa n)))
      (princ (strcat "\nBiblioteca MEMO_Lib: " (if memo:portapapeles "OK" "NO CARGADA")))
      (foreach e (reverse err) (princ (strcat "\n  ERROR AL CARGAR: " e)))
      (foreach f (reverse faltan) (princ (strcat "\n  NO DEFINIDO:     " f)))
      (if (and (not err) (not faltan)) (princ "\n  Todo correcto."))
      (princ "\n================================================")))
  (princ))

;;; Compila todos los LISP a FAS (carga más rápida, código protegido).
(defun c:MEMO_COMPILAR (/ base ok mal res f lista)
  (if (not vlisp-compile)
    (princ "\nEsta versión de AutoCAD no tiene vlisp-compile; se siguen usando los .lsp.")
    (progn
      (setq base (strcat (vl-string-translate "\\" "/" (getenv "APPDATA")) "/MEMO_SISTEMA"))
      (vl-mkdir base)
      (vl-mkdir (strcat base "/FAS"))
      (setq ok 0 lista (cons "Sistema/MEMO_Lib" (mapcar 'car memo:*mapa*)))
      (foreach rel lista
        (princ (strcat "\nCompilando " rel "..."))
        (setq res (vl-catch-all-apply 'vlisp-compile
                    (list 'st (strcat memo:raiz "/LISP/" rel ".lsp")
                              (strcat memo:dir-fas (vl-filename-base rel) ".fas"))))
        (if (and res (not (vl-catch-all-error-p res)))
          (setq ok (1+ ok))
          (setq mal (cons rel mal))))
      (if (and (> ok 0) (setq f (open (strcat memo:dir-fas "version.txt") "w")))
        (progn (write-line memo:version f) (close f)))
      (textscr)
      (princ (strcat "\n\nCompilados: " (itoa ok) " de " (itoa (length lista)) " en " memo:dir-fas))
      (foreach m (reverse mal) (princ (strcat "\n  No se compiló (se usará el .lsp): " m)))
      (princ "\nLos FAS se usan desde el próximo dibujo que abras.")
      (princ "\nPara volver a los .lsp, borre la carpeta FAS. Al actualizar el sistema se ignoran solos.")))
  (princ))

(princ)
