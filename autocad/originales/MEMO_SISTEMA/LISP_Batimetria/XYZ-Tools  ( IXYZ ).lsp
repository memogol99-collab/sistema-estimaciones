;;; ============================================================================
;;; XYZ-Tools 2.6.2 | 2026-11-05 | MEJORA DE COMANDOS - Guillermo Michel
;;; Un solo LSP. DCL temporal integrado. AutoCAD / ZWCAD para Windows.
;;; COMANDOS: XYZ IXYZ PZ P-Z IZ OZ ZM XYZU XYZUNIR XYZAYUDA XYZLOTES XYZBORRAR XYZRESTAURAR XYZTEST
;;; BASE FUNCIONAL: XYZ-Tools 2.3 (archivo entregado por Guillermo).
;;; Conserva XYZ / IXYZ / PZ, etiquetas y los cinco modos de procesamiento.
;;; Integra correcciones del motor IXYZ 7.0.1 ya validado por el usuario.
;;; 2.6.2: corrige LAST en clases extremas, filtros por poligono y rangos Z.
;;; 2.6.1: simbologia con clases << inferior y >> superior.
;;; 2.6.0: exportar seleccion POINT; intervalos redondeados; simbologia tras importar.
;;; 2.5.0: integra IZ/OZ/ZM en dibujo, P-Z y XYZU de Procesa_Puntos;
;;; conserva DCL integrado, rangos sin doble aplicacion y union secuencial;
;;; salidas temporales, fuentes protegidas, decimales configurables, lotes y CSV.
;;; Pruebas automatizadas/simuladas; integracion nativa CAD pendiente.
;;; ============================================================================
(vl-load-com)
(setq *xyzt:version* "2.6.2")
;; Configuracion y estados de capa duran la sesion; datos de lote quedan en DWG.

(defun xyzt:get (key cfg) (cdr (assoc key cfg)))
(defun xyzt:put (key val cfg / a)
  (if (setq a (assoc key cfg)) (subst (cons key val) a cfg)
    (cons (cons key val) cfg)))
(defun xyzt:trim (s) (vl-string-trim (strcat " " (chr 9) (chr 13) (chr 10)) s))
(defun xyzt:fail (s) (setq *xyzt:failure* (strcat "IXYZ: " s)) (exit))
(defun xyzt:try (fn args) (setq *xyzt:failure* nil) (vl-catch-all-apply fn args))
(defun xyzt:errmsg (err) (if *xyzt:failure* *xyzt:failure* (vl-catch-all-error-message err)))
(defun xyzt:make (data / en)
  (if (entmake data) (entlast) (xyzt:fail "No se pudo crear una entidad grafica.")))
(defun xyzt:nstr (v / old out)
  (setq old (getvar "DIMZIN"))
  (setvar "DIMZIN" 0)
  (setq out (rtos v 2 8))
  (setvar "DIMZIN" old)
  out)
(defun xyzt:floor (v / n)
  (if (> (abs v) 2147483000.0)
    (setq n (atof (rtos (- v (rem v 1.0)) 2 0)))
    (setq n (fix v)))
  (if (< v n) (- n 1) n))
(defun xyzt:hex (rgb / out digits n)
  (setq digits "0123456789ABCDEF" out "#")
  (foreach n rgb
    (setq out (strcat out (substr digits (1+ (/ n 16)) 1)
      (substr digits (1+ (rem n 16)) 1)))) out)
(defun xyzt:percent (part total)
  (if (> total 0) (* 100.0 (/ (float part) total)) 0.0))
(defun xyzt:tc (rgb) (+ (* (car rgb) 65536) (* (cadr rgb) 256) (caddr rgb)))

;;; Numeros estrictos: signo, decimal elegido y exponente E/D. Sin separadores
;;; de millares ni unidades. Cero es valido. No depende de LUNITS.
(defun xyzt:number (s decimal / i n ch digits dot expo expdigits expstart ok norm)
  (setq s (xyzt:trim s) i 1 n (strlen s) digits 0 dot nil expo nil
        expdigits 0 expstart nil ok T norm "")
  (if (and (> n 0) (member (substr s 1 1) '("+" "-")))
    (setq norm (substr s 1 1) i 2))
  (while (and ok (<= i n))
    (setq ch (strcase (substr s i 1)))
    (cond
      ((and (>= (ascii ch) 48) (<= (ascii ch) 57))
        (if expo (setq expdigits (1+ expdigits)) (setq digits (1+ digits)))
        (setq norm (strcat norm ch) expstart nil))
      ((and (= ch decimal) (not dot) (not expo))
        (setq dot T norm (strcat norm ".")))
      ((and (member ch '("E" "D")) (not expo) (> digits 0))
        (setq expo T expstart T norm (strcat norm "E")))
      ((and expstart (member ch '("+" "-")))
        (setq norm (strcat norm ch) expstart nil))
      (T (setq ok nil)))
    (setq i (1+ i)))
  (if (and ok (> digits 0) (or (not expo) (> expdigits 0)))
    (distof norm (if expo 1 2)) nil))

(defun xyzt:setting-number (s / value)
  ;; OR en AutoLISP devuelve T/nil, nunca el numero encontrado.
  (setq value (xyzt:number s "."))
  (if (null value) (setq value (xyzt:number s ",")))
  value)

;;; Campos CSV con comillas dobles escapadas. WS colapsa espacios y tabs.
;;; Retorna nil si hay comillas sin cerrar o caracteres tras una comilla final.
(defun xyzt:fields (s sep / i n ch out field quoted afterq started valid delim)
  (setq i 1 n (strlen s) out nil field "" quoted nil afterq nil started nil valid T)
  (while (and valid (<= i n))
    (setq ch (substr s i 1)
          delim (if (= sep "WS") (member ch (list " " (chr 9))) (= ch sep)))
    (cond
      (quoted
        (if (= ch "\"")
          (if (and (< i n) (= (substr s (1+ i) 1) "\""))
            (setq field (strcat field "\"") i (1+ i))
            (setq quoted nil afterq T))
          (setq field (strcat field ch))))
      (delim
        (if (or (/= sep "WS") started afterq)
          (setq out (cons (xyzt:trim field) out)))
        (setq field "" afterq nil started nil))
      (afterq (if (/= ch " ") (setq valid nil)))
      ((= ch "\"")
        (if (= (xyzt:trim field) "") (setq field "" quoted T started T)
          (setq valid nil)))
      (T (setq field (strcat field ch) started T)))
    (setq i (1+ i)))
  (if (or quoted (not valid)) nil
    (progn
      (if (or (/= sep "WS") started afterq) (setq out (cons (xyzt:trim field) out)))
      (reverse out))))
(defun xyzt:separator (cfg)
  (nth (atoi (xyzt:get "sep" cfg)) (list "AUTO" "WS" (chr 9) ";" ",")))
(defun xyzt:decimal (cfg) (if (= (xyzt:get "decimal" cfg) "1") "," "."))
(defun xyzt:line (s cfg sep / fields x y z maxcol dec)
  (setq fields (xyzt:fields s sep) dec (xyzt:decimal cfg)
        maxcol (max (atoi (xyzt:get "cx" cfg)) (atoi (xyzt:get "cy" cfg))
                    (atoi (xyzt:get "cz" cfg))))
  (if (and fields (>= (length fields) maxcol)
           (setq x (xyzt:number (nth (1- (atoi (xyzt:get "cx" cfg))) fields) dec))
           (setq y (xyzt:number (nth (1- (atoi (xyzt:get "cy" cfg))) fields) dec))
           (setq z (xyzt:number (nth (1- (atoi (xyzt:get "cz" cfg))) fields) dec)))
    (progn
      (setq x (* x (xyzt:get 'xyfactor cfg)) y (* y (xyzt:get 'xyfactor cfg))
            z (+ (* z (xyzt:get 'zfactor cfg)) (xyzt:get 'offset cfg)))
      (if (and (<= (abs x) 1e9) (<= (abs y) 1e9) (<= (abs z) 1e7))
        (list x y z) nil)) nil))
(defun xyzt:comment (s / v)
  (setq v (xyzt:trim s))
  (or (= v "") (member (substr v 1 1) '("#" ";"))
      (= (substr v 1 2) "//")))
(defun xyzt:header (s cfg sep / fields vals)
  (setq fields (xyzt:fields s sep))
  (if fields
    (progn
      (setq vals (mapcar '(lambda (key / v)
        (setq v (nth (1- (atoi (xyzt:get key cfg))) fields))
        (if v (strcase (xyzt:trim v)) "")) '("cx" "cy" "cz")))
      (and (member (car vals) '("X" "E" "ESTE" "EASTING" "Y" "N" "NORTE" "NORTHING"))
           (member (cadr vals) '("X" "E" "ESTE" "EASTING" "Y" "N" "NORTE" "NORTHING"))
           (member (caddr vals) '("Z" "COTA" "ELEVACION" "ELEVATION" "DEPTH" "PROFUNDIDAD"))))))
(defun xyzt:read-line (f / s)
  (setq s (read-line f))
  (if (and s (> (strlen s) 0) (= (ascii (substr s 1 1)) 65279)) (setq s (substr s 2)))
  (if (and s (>= (strlen s) 3) (= (ascii (substr s 1 1)) 239)
           (= (ascii (substr s 2 1)) 187) (= (ascii (substr s 3 1)) 191))
    (setq s (substr s 4))) s)
(defun xyzt:open-input (path / f)
  (if (not (setq f (open path "r"))) (xyzt:fail "No se pudo abrir el archivo de entrada."))
  (setq *xyzt:in* f) f)
(defun xyzt:close-input ()
  (if *xyzt:in* (progn (close *xyzt:in*) (setq *xyzt:in* nil))))
(defun xyzt:detect (cfg / f s ln seen candidates scores sep score p best bestscore ties pair)
  (setq sep (xyzt:separator cfg))
  (if (/= sep "AUTO") sep
    (progn
      (setq candidates (if (= (xyzt:decimal cfg) ",") (list "WS" (chr 9) ";")
                         (list "WS" (chr 9) ";" ","))
            scores (mapcar '(lambda (v) (cons v 0)) candidates)
            f (xyzt:open-input (xyzt:get "file" cfg)) ln 0 seen 0)
      (while (and (< seen 100) (setq s (xyzt:read-line f)))
        (setq ln (1+ ln))
        (if (and (> ln (atoi (xyzt:get "skip" cfg))) (not (xyzt:comment s)))
          (progn
            (setq seen (1+ seen))
            (foreach sep candidates
              (if (xyzt:line s cfg sep)
                (setq scores (xyzt:put sep (1+ (xyzt:get sep scores)) scores)))))))
      (xyzt:close-input)
      (setq best nil bestscore 0 ties nil)
      (foreach pair scores
        (cond ((> (cdr pair) bestscore) (setq best (car pair) bestscore (cdr pair) ties nil))
              ((and (> (cdr pair) 0) (= (cdr pair) bestscore))
                ;; TAB y WS equivalen en archivos tabulados: preferir WS.
                (if (not (and (= best "WS") (= (car pair) (chr 9)))) (setq ties T)))))
      (if (or (not best) ties)
        (xyzt:fail "Separador automatico ambiguo o sin puntos. Elija el separador y revise columnas/decimales."))
      best)))

;;; Configuracion con claves, persistente durante la sesion.
(defun xyzt:defaults ()
  '(("file" . "") ("sep" . "0") ("decimal" . "0") ("cx" . "1") ("cy" . "2")
    ("cz" . "3") ("skip" . "0") ("units" . "0") ("zmode" . "0") ("dz" . "0")
    ("ref" . "No especificada") ("crs" . "No especificado") ("prefix" . "XYZ")
    ("palette" . "0") ("classmode" . "0") ("classes" . "10") ("step" . "0.5")
    ("base" . "0") ("top" . "10") ("outside" . "0") ("reduce" . "0")
    ("every" . "1") ("spacing" . "1") ("duplicates" . "0") ("tol" . "0.001")
    ("xyfilter" . "0") ("xmin" . "0") ("xmax" . "0") ("ymin" . "0") ("ymax" . "0")
    ("zfilter" . "0") ("zmin" . "-1000") ("zmax" . "1000")
    ("legend" . "1") ("height" . "1") ("csv" . "1") ("zoom" . "1")
    ("isolate" . "0") ("backup" . "0") ("outdir" . "") ("pdsize" . "0")
    ("labels" . "0") ("labelheight" . "0.6") ("labelwidth" . "0.7") ("labelsep" . "1.2")
    ("labeldec" . "2") ("labelabs" . "0") ("labelone" . "0") ("labellayer" . "ETIQUETAS_Z")
    ("labelstyle" . "MONOTXT4") ("labelz" . "0")))
(setq xyzt:keys '("file" "sep" "decimal" "cx" "cy" "cz" "skip" "units" "zmode" "dz" "ref" "crs" "prefix" "palette" "classmode" "classes" "step" "base" "top" "outside" "reduce" "every" "spacing" "duplicates" "tol" "xyfilter" "xmin" "xmax" "ymin" "ymax" "zfilter" "zmin" "zmax" "legend" "height" "csv" "zoom" "isolate" "backup" "outdir" "pdsize"))
(defun xyzt:validate (cfg / key val cols factor num step base top count prefix)
  (if (or (= (xyzt:get "file" cfg) "") (not (findfile (xyzt:get "file" cfg))))
    (xyzt:fail "Seleccione un archivo existente."))
  (foreach key '("cx" "cy" "cz" "skip" "classes" "every")
    (setq val (xyzt:number (xyzt:get key cfg) "."))
    (if (or (null val) (/= val (fix val))
            (< val (if (= key "skip") 0 1)) (> val 1000000000))
      (xyzt:fail (strcat "Entero invalido: " key))))
  (setq cols (mapcar '(lambda (k) (atoi (xyzt:get k cfg))) '("cx" "cy" "cz")))
  (if (or (= (car cols) (cadr cols)) (= (car cols) (caddr cols)) (= (cadr cols) (caddr cols)))
    (xyzt:fail "X, Y y Z deben usar columnas distintas."))
  (if (> (apply 'max cols) 1000) (xyzt:fail "Maximo 1000 columnas."))
  (foreach key '("dz" "step" "base" "top" "spacing" "tol" "xmin" "xmax" "ymin" "ymax" "zmin" "zmax" "height" "pdsize")
    (setq val (xyzt:setting-number (xyzt:get key cfg)))
    (if (or (null val) (> (abs val) 1e12)) (xyzt:fail (strcat "Numero invalido: " key)))
    (setq cfg (xyzt:put (read (strcat "v-" key)) val cfg)))
  (foreach key '("step" "spacing" "tol" "height")
    (if (<= (xyzt:get (read (strcat "v-" key)) cfg) 0) (xyzt:fail (strcat key " debe ser mayor que cero."))))
  (if (or (< (xyzt:get 'v-spacing cfg) 0.000001) (< (xyzt:get 'v-tol cfg) 0.000001))
    (xyzt:fail "Celda/distancia y tolerancia: minimo 0.000001 m."))
  (if (> (atoi (xyzt:get "classes" cfg)) 100) (xyzt:fail "Maximo 100 clases."))
  (if (and (= (xyzt:get "sep" cfg) "4") (= (xyzt:decimal cfg) ","))
    (xyzt:fail "Coma decimal y coma separadora son ambiguas. Use punto y coma o TAB."))
  (if (and (= (xyzt:get "xyfilter" cfg) "1")
      (or (> (xyzt:get 'v-xmin cfg) (xyzt:get 'v-xmax cfg)) (> (xyzt:get 'v-ymin cfg) (xyzt:get 'v-ymax cfg))))
    (xyzt:fail "Limites XY invertidos."))
  (if (and (= (xyzt:get "zfilter" cfg) "1") (> (xyzt:get 'v-zmin cfg) (xyzt:get 'v-zmax cfg)))
    (xyzt:fail "Limites Z invertidos."))
  (if (and (= (xyzt:get "classmode" cfg) "2") (>= (xyzt:get 'v-base cfg) (xyzt:get 'v-top cfg)))
    (xyzt:fail "El limite superior comun debe superar al inferior."))
  (setq prefix (xyzt:trim (xyzt:get "prefix" cfg)))
  (if (or (= prefix "") (> (strlen prefix) 40) (not (snvalid prefix)))
    (xyzt:fail "Prefijo de capa invalido (maximo 40 caracteres)."))
  (if (or (> (strlen (xyzt:get "ref" cfg)) 120) (> (strlen (xyzt:get "crs" cfg)) 120))
    (xyzt:fail "Referencia y sistema: maximo 120 caracteres."))
  (setq factor (nth (atoi (xyzt:get "units" cfg)) '(1.0 0.3048 0.001)))
  (setq cfg (xyzt:put 'xyfactor factor cfg)
        cfg (xyzt:put 'zfactor (* factor (if (= (xyzt:get "zmode" cfg) "0") 1.0 -1.0)) cfg)
        cfg (xyzt:put 'offset (xyzt:get 'v-dz cfg) cfg))
  (if (and (/= (xyzt:get "outdir" cfg) "") (not (vl-file-directory-p (xyzt:get "outdir" cfg))))
    (xyzt:fail "La carpeta de salida no existe."))
  (xyz:validate-labels cfg))

;;; Poligono: LWPOLYLINE cerrada, recta, horizontal. Vertices convertidos a WCS.
(defun xyzt:polygon (/ sel en ed verts bulge normal item q)
  (setq sel (entsel "\nSeleccione polilinea cerrada sin arcos para filtro XY: "))
  (if sel
    (progn
      (setq en (car sel) ed (entget en) verts nil bulge nil normal (cdr (assoc 210 ed)))
      (if (or (/= (cdr (assoc 0 ed)) "LWPOLYLINE")
              (= 0 (logand 1 (cdr (assoc 70 ed))))
              (and normal (not (equal normal '(0.0 0.0 1.0) 1e-9))))
        (xyzt:fail "Use una LWPOLYLINE cerrada horizontal con normal +Z."))
      (foreach item ed
        (if (and (= (car item) 42) (/= (cdr item) 0.0)) (setq bulge T))
        (if (= (car item) 10)
          (progn (setq q (trans (list (cadr item) (caddr item) (cond ((cdr (assoc 38 ed))) (T 0.0))) en 0))
                 (setq verts (cons (list (car q) (cadr q)) verts)))))
      (if (or bulge (< (length verts) 3)) (xyzt:fail "El filtro requiere al menos 3 vertices y ningun arco."))
      (reverse verts))))
(defun xyzt:on-segment (p a b / dx dy len2 u q)
  (setq dx (- (car b) (car a)) dy (- (cadr b) (cadr a)) len2 (+ (* dx dx) (* dy dy)))
  (if (= len2 0.0) (equal (list (car p) (cadr p)) a 1e-8)
    (progn
      (setq u (/ (+ (* (- (car p) (car a)) dx) (* (- (cadr p) (cadr a)) dy)) len2))
      (and (>= u -1e-10) (<= u 1.0000000001)
           (<= (abs (- (* (- (car p) (car a)) dy) (* (- (cadr p) (cadr a)) dx)))
               (* 1e-8 (sqrt len2)))))))
(defun xyzt:inside (p poly / a b hit boundary)
  (setq a (last poly) hit nil boundary nil)
  (foreach b poly
    (if (xyzt:on-segment p a b) (setq boundary T))
    (if (and (not (eq (> (cadr a) (cadr p)) (> (cadr b) (cadr p))))
             (< (car p) (+ (car a) (* (- (car b) (car a))
                  (/ (- (cadr p) (cadr a)) (- (cadr b) (cadr a)))))))
      (setq hit (not hit)))
    (setq a b))
  (or boundary hit))
(defun xyzt:filter-reason (p cfg poly)
  (cond
    ((or (> (abs (car p)) 1e10) (> (abs (cadr p)) 1e10) (> (abs (caddr p)) 1e8)) "RANGO_NUMERICO")
    ((and (= (xyzt:get "xyfilter" cfg) "1")
      (or (< (car p) (xyzt:get 'v-xmin cfg)) (> (car p) (xyzt:get 'v-xmax cfg))
          (< (cadr p) (xyzt:get 'v-ymin cfg)) (> (cadr p) (xyzt:get 'v-ymax cfg)))) "FUERA_XY")
    ((and poly (not (xyzt:inside p poly))) "FUERA_POLIGONO")
    ((and (= (xyzt:get "zfilter" cfg) "1")
      (or (< (caddr p) (xyzt:get 'v-zmin cfg)) (> (caddr p) (xyzt:get 'v-zmax cfg)))) "FUERA_Z")
    (T nil)))
(defun xyzt:welford (state z / n mean m2 delta)
  (setq n (1+ (car state)) delta (- z (cadr state)) mean (+ (cadr state) (/ delta n))
        m2 (+ (caddr state) (* delta (- z mean))))
  (list n mean m2))
(defun xyzt:stat-add (s p / z)
  (setq z (caddr p))
  (list (xyzt:welford (car s) z)
    (if (cadr s) (min (cadr s) z) z) (if (caddr s) (max (caddr s) z) z)
    (if (nth 3 s) (mapcar 'min (nth 3 s) p) p)
    (if (nth 4 s) (mapcar 'max (nth 4 s) p) p)))
(defun xyzt:empty-stat () (list '(0 0.0 0.0) nil nil nil nil))
(defun xyzt:std (s / w) (setq w (car s))
  (if (> (car w) 1) (sqrt (max 0.0 (/ (caddr w) (1- (car w))))) 0.0))
(defun xyzt:analyze (cfg poly sep / f s ln p reason raw eligible counts skipped invalid)
  (setq f (xyzt:open-input (xyzt:get "file" cfg)) ln 0 raw (xyzt:empty-stat)
        eligible (xyzt:empty-stat) counts nil skipped 0 invalid 0)
  (while (setq s (xyzt:read-line f))
    (setq ln (1+ ln))
    (cond
      ((or (<= ln (atoi (xyzt:get "skip" cfg))) (xyzt:comment s) (xyzt:header s cfg sep))
        (setq skipped (1+ skipped)))
      ((not (setq p (xyzt:line s cfg sep))) (setq invalid (1+ invalid)))
      (T
        (setq raw (xyzt:stat-add raw p) reason (xyzt:filter-reason p cfg poly))
        (if reason (setq counts (xyzt:put reason (1+ (cond ((xyzt:get reason counts)) (T 0))) counts))
          (setq eligible (xyzt:stat-add eligible p)))))
    (if (= 0 (rem ln 20000)) (princ (strcat "\rXYZ-Tools analizando " (itoa ln) " lineas..."))))
  (xyzt:close-input)
  (list (cons 'raw raw) (cons 'eligible eligible) (cons 'lines ln)
        (cons 'skip skipped) (cons 'invalid invalid) (cons 'filtered counts)))
(defun xyzt:stats-text (stats / raw sel)
  (setq raw (xyzt:get 'raw stats) sel (xyzt:get 'eligible stats))
  (strcat "Archivo: " (itoa (car (car raw))) " XYZ validos; "
    (itoa (xyzt:get 'invalid stats)) " invalidos; " (itoa (xyzt:get 'skip stats)) " omitidos.\n"
    "Dentro de filtros: " (itoa (car (car sel)))
    (if (> (car (car sel)) 0)
      (strcat " | Z " (rtos (cadr sel) 2 3) " a " (rtos (caddr sel) 2 3)
        "\nPromedio Z: " (rtos (cadr (car sel)) 2 3) " | Desv. muestral: " (rtos (xyzt:std sel) 2 3)
        "\nX: " (rtos (car (nth 3 sel)) 2 3) " a " (rtos (car (nth 4 sel)) 2 3)
        " | Y: " (rtos (cadr (nth 3 sel)) 2 3) " a " (rtos (cadr (nth 4 sel)) 2 3)) "")))

;;; Clases: [inferior,superior), ultimo incluye maximo. Maximo 100.
(defun xyzt:nice-step (raw / scale choice candidate)
  (if (<= raw 0.0) 0.5
    (progn
      (setq scale 1.0 choice nil)
      (while (> raw (* 5.0 scale)) (setq scale (* scale 10.0)))
      (while (< raw (* 0.5 scale)) (setq scale (/ scale 10.0)))
      (foreach candidate '(0.5 1.0 2.0 2.5 5.0)
        (if (and (null choice) (<= raw (* candidate scale))) (setq choice (* candidate scale))))
      choice)))
(defun xyzt:classes (cfg stats lot / s lo hi step count mode i out upper)
  (setq s (xyzt:get 'eligible stats) lo (cadr s) hi (caddr s) mode (atoi (xyzt:get "classmode" cfg)))
  (setq step
    (if (= mode 0)
      (if (equal lo hi 1e-12) (xyzt:get 'v-step cfg)
        (xyzt:nice-step (/ (- hi lo) (atoi (xyzt:get "classes" cfg)))))
      (xyzt:get 'v-step cfg)))
  (if (= mode 2) (setq lo (xyzt:get 'v-base cfg) hi (xyzt:get 'v-top cfg)))
  ;; Limites completos y multiplos del intervalo, tambien para cotas negativas.
  (setq lo (* step (xyzt:floor (+ (/ lo step) 1e-10)))
        hi (* step (xyzt:ceil (/ hi step)))
        count (max 1 (xyzt:ceil (/ (- hi lo) step))) hi (+ lo (* count step)))
  (if (> count 100) (xyzt:fail "Mas de 100 intervalos. Aumente el intervalo o use Automatico redondeado."))
  (setq i 0 out nil)
  (repeat count
    (setq upper (+ lo (* (1+ i) step)))
    (setq out (cons (list (strcat (xyzt:get "prefix" cfg) "_" lot "_" (if (< i 9) "0" "") (itoa (1+ i)))
      (+ lo (* i step)) upper (xyzt:rgb-ccn (1+ i) count (= (xyzt:get "palette" cfg) "1"))) out))
    (setq i (1+ i)))
  (xyzt:add-tails (reverse out) cfg lot))
(defun xyzt:ceil (v / n) (setq n (fix v)) (if (> v (+ n 1e-10)) (1+ n) n))
(defun xyzt:tail-kind (info) (nth 4 info))
(defun xyzt:class-label (info)
  (cond
    ((eq (xyzt:tail-kind info) 'UNDER) (strcat "<< " (rtos (nth 2 info) 2 2)))
    ((eq (xyzt:tail-kind info) 'OVER) (strcat ">> " (rtos (nth 1 info) 2 2)))
    (T (strcat (rtos (nth 1 info) 2 2) " a " (rtos (nth 2 info) 2 2)))))
(defun xyzt:class-bound (info index)
  (if (or (and (= index 1) (eq (xyzt:tail-kind info) 'UNDER))
          (and (= index 2) (eq (xyzt:tail-kind info) 'OVER))) ""
    (xyzt:nstr (nth index info))))
(defun xyzt:add-tails (classes cfg lot / count index out info low high)
  (setq low (nth 1 (car classes)) high (nth 2 (last classes))
        count (+ (length classes) 2) index 2 out nil)
  (foreach info classes
    (setq out (cons (list (car info) (nth 1 info) (nth 2 info)
      (xyzt:rgb-ccn index count (= (xyzt:get "palette" cfg) "1"))) out) index (1+ index)))
  (append
    (list (list (strcat (xyzt:get "prefix" cfg) "_" lot "_BAJO") -1e99 low
      (xyzt:rgb-ccn 1 count (= (xyzt:get "palette" cfg) "1")) 'UNDER))
    (reverse out)
    (list (list (strcat (xyzt:get "prefix" cfg) "_" lot "_ALTO") high 1e99
      (xyzt:rgb-ccn count count (= (xyzt:get "palette" cfg) "1")) 'OVER))))
(defun xyzt:class-index (z classes outside / i found info kind next)
  (setq i 0 found nil)
  (foreach info classes
    (setq kind (xyzt:tail-kind info) next (nth (1+ i) classes))
    (if (null found)
      (cond
        ((eq kind 'UNDER) (if (and (= outside "1") (< z (nth 2 info))) (setq found i)))
        ((eq kind 'OVER) (if (and (= outside "1") (> z (nth 1 info))) (setq found i)))
        ((and (>= z (nth 1 info))
              (or (< z (nth 2 info))
                  (and (or (not next) (eq (xyzt:tail-kind next) 'OVER)) (<= z (nth 2 info)))))
          (setq found i))))
    (setq i (1+ i)))
  ;; Compatibilidad para listas antiguas sin clases abiertas.
  (if (and (null found) (= outside "1") (not (eq (xyzt:tail-kind (car classes)) 'UNDER)))
    (setq found (if (< z (nth 1 (car classes))) 0 (1- (length classes))))) found)
;;; Indice hash en SafeArray de cadenas: sin Scripting.Dictionary ni librerias
;;; COM externas. 65521 cubetas; cada cubeta contiene solo sus colisiones.
(defun xyzt:new-dict (/ obj)
  (setq obj (vl-catch-all-apply 'vlax-make-safearray (list 8 (cons 0 65520))))
  (if (vl-catch-all-error-p obj)
    (xyzt:fail "No disponible indice espacial SafeArray. Use Sin reduccion/Cada N y sin duplicados."))
  obj)
(defun xyzt:unvariant (v)
  (if (eq (type v) 'VARIANT) (vlax-variant-value v) v))
(defun xyzt:hash (key / i code)
  (setq i 1 code 0)
  (while (<= i (strlen key))
    (setq code (rem (+ (* code 31) (ascii (substr key i 1))) 65521) i (1+ i))) code)
(defun xyzt:bucket (d key / value)
  (setq value (xyzt:unvariant (vlax-safearray-get-element d (xyzt:hash key))))
  (if (and (eq (type value) 'STR) (/= value "")) (read value) nil))
(defun xyzt:dict-get (d key) (cadr (assoc key (xyzt:bucket d key))))
(defun xyzt:serialize (v / out item)
  (cond
    ((null v) "nil")
    ((eq (type v) 'REAL) (rtos v 2 16))
    ((eq (type v) 'INT) (itoa v))
    ((eq (type v) 'LIST)
      (setq out "(")
      (foreach item v (setq out (strcat out (xyzt:serialize item) " ")))
      (strcat out ")"))
    (T (vl-prin1-to-string v))))
(defun xyzt:dict-set (d key val / bucket previous)
  (setq bucket (xyzt:bucket d key) previous (assoc key bucket))
  (setq bucket (if previous (subst (list key val) previous bucket) (cons (list key val) bucket)))
  (vlax-safearray-put-element d (xyzt:hash key) (xyzt:serialize bucket)))
(defun xyzt:cell (p size) (list (xyzt:floor (/ (car p) size)) (xyzt:floor (/ (cadr p) size))))
(defun xyzt:cell3 (p size)
  (append (xyzt:cell p size) (list (xyzt:floor (/ (caddr p) size)))))
(defun xyzt:cellkey (cell)
  (strcat (rtos (car cell) 2 0) ":" (rtos (cadr cell) 2 0)
    (if (caddr cell) (strcat ":" (rtos (caddr cell) 2 0)) "")))
(defun xyzt:distance2 (a b dims / dx dy dz)
  (setq dx (- (car a) (car b)) dy (- (cadr a) (cadr b))
        dz (if (= dims 3) (- (caddr a) (caddr b)) 0.0))
  (+ (* dx dx) (* dy dy) (* dz dz)))
(defun xyzt:near (dict p size dims / cell dx dy dz vals found q neighbor)
  (setq cell (if (= dims 3) (xyzt:cell3 p size) (xyzt:cell p size)) dx -1 found nil)
  (repeat 3
    (setq dy -1)
    (repeat 3
      (setq dz (if (= dims 3) -1 0))
      (repeat (if (= dims 3) 3 1)
        (setq neighbor (list (+ (car cell) dx) (+ (cadr cell) dy)))
        (if (= dims 3) (setq neighbor (append neighbor (list (+ (caddr cell) dz)))))
        (setq vals (xyzt:dict-get dict (xyzt:cellkey neighbor)))
        (foreach q vals (if (< (xyzt:distance2 p q dims) (* size size)) (setq found T)))
        (setq dz (1+ dz)))
      (setq dy (1+ dy)))
    (setq dx (1+ dx))) found)
(defun xyzt:store-near (dict p size dims / key)
  (setq key (xyzt:cellkey (if (= dims 3) (xyzt:cell3 p size) (xyzt:cell p size))))
  (xyzt:dict-set dict key (cons p (xyzt:dict-get dict key))))
(defun xyzt:exact-key (p) (xyzt:serialize p))
(defun xyzt:duplicate (d p cfg / mode key tol found)
  (setq mode (xyzt:get "duplicates" cfg))
  (cond
    ((= mode "0") nil)
    ((= mode "1")
      (setq key (xyzt:exact-key p) found (xyzt:dict-get d key))
      (if (not found) (xyzt:dict-set d key T)) found)
    (T (setq tol (xyzt:get 'v-tol cfg) found (xyzt:near d p tol 3))
       (if (not found) (xyzt:store-near d p tol 3)) found)))
(defun xyzt:grid-better (new old mode)
  (or (not old)
      (and (= mode 3) (> (caddr (car new)) (caddr (car old))))
      (and (= mode 4) (< (caddr (car new)) (caddr (car old))))))

;;; XData ligero: lote y linea fuente. El resto se registra una vez en XRECORD.
(defun xyzt:tag (lot line)
  (list -3 (list "IXYZ7" (cons 1000 lot) (cons 1071 line))))
(defun xyzt:lot-of (en / data app)
  (setq data (entget en '("IXYZ7")) app (cadr (assoc -3 data)))
  (if (equal (car app) "IXYZ7") (cdr (assoc 1000 (cdr app))) nil))
(defun xyzt:lot-selection (lot / ss out i en)
  (setq ss (ssget "_X" '((-3 ("IXYZ7")))) out nil)
  (if ss
    (progn (setq i 0)
      (repeat (sslength ss)
        (setq en (ssname ss (float i)))
        (if (= lot (xyzt:lot-of en)) (setq out (cons en out)))
        (setq i (1+ i))))) out)
(defun xyzt:root (/ found en)
  (if (setq found (dictsearch (namedobjdict) "IXYZ7_LOTES")) (cdr (assoc -1 found))
    (progn (setq en (entmakex '((0 . "DICTIONARY") (100 . "AcDbDictionary") (280 . 0) (281 . 1))))
      (if (not en) (xyzt:fail "No se pudo crear el registro de lotes."))
      (dictadd (namedobjdict) "IXYZ7_LOTES" en))))
(defun xyzt:chunk-record (data / out item value)
  (setq out nil)
  (foreach item data
    (if (and (= (car item) 1) (> (strlen (cdr item)) 250))
      (progn
        (setq value (cdr item))
        (while (> (strlen value) 250)
          (setq out (cons (cons 1 (substr value 1 250)) out) value (substr value 251)))
        (setq out (cons (cons 1 value) out)))
      (setq out (cons item out))))
  (reverse out))
(defun xyzt:record (lot cfg classes stats imported counts / data pair item en root)
  (setq data (list '(0 . "XRECORD") '(100 . "AcDbXrecord") '(280 . 1)
    (cons 1 (strcat "XYZ-Tools " *xyzt:version* " | " lot))
    (cons 1 (strcat "FUENTE=" (xyzt:get "file" cfg)))
    (cons 1 (strcat "CREADO=" (rtos (getvar "CDATE") 2 6)))
    (cons 1 (strcat "IMPORTADOS=" (itoa imported)))
    (cons 1 "SALIDA=metros WCS; Z=elevacion; sin reproyeccion")))
  (foreach pair cfg
    (if (and (eq (type (car pair)) 'STR) (/= (car pair) "file"))
      (setq data (append data (list (cons 1 (strcat (car pair) "=" (cdr pair))))))))
  (if *xyzt:polygon*
    (setq data (append data (list (cons 1 (strcat "POLIGONO_WCS=" (xyzt:serialize *xyzt:polygon*)))))))
  (if *xyzt:replace*
    (setq data (append data (list (cons 1 (strcat "REEMPLAZA_LOTE=" *xyzt:replace*))))))
  (foreach item classes
    (setq data (append data (list (cons 1 (strcat "CLASE=" (car item) ";"
      (xyzt:class-bound item 1) ";" (xyzt:class-bound item 2) ";" (xyzt:hex (nth 3 item))))))))
  (foreach pair counts
    (setq data (append data (list (cons 1 (strcat "CONTADOR=" (car pair) ";" (itoa (cdr pair))))))))
  (setq data (xyzt:chunk-record data))
  (setq root (xyzt:root) en (entmakex data))
  (if (or (not en) (not (dictadd root lot en))) (xyzt:fail "No se pudo registrar el lote."))
  en)
(defun xyzt:lot-id (/ base lot i root)
  (setq base (strcat "L" (vl-string-translate "." "_" (rtos (getvar "CDATE") 2 6)))
        lot base i 1 root (dictsearch (namedobjdict) "IXYZ7_LOTES"))
  (if root (setq root (cdr (assoc -1 root))))
  (while (and root (dictsearch root lot)) (setq lot (strcat base "_" (itoa i)) i (1+ i))) lot)
(defun xyzt:layer (name rgb / en)
  (if (tblsearch "LAYER" name) (xyzt:fail "Colision inesperada de capa; cambie prefijo."))
  (setq en (entmake (list '(0 . "LAYER") '(100 . "AcDbSymbolTableRecord")
      '(100 . "AcDbLayerTableRecord") (cons 2 name) '(70 . 0) '(62 . 7)
      (cons 420 (xyzt:tc rgb)) '(6 . "Continuous"))))
  (if (not en) (xyzt:fail (strcat "No se pudo crear capa " name)))
  (setq *xyzt:newlayers* (cons name *xyzt:newlayers*)) en)
(defun xyzt:point (p line lot layer)
  (xyzt:make (list '(0 . "POINT") '(100 . "AcDbEntity") (cons 8 layer) '(62 . 256)
    '(100 . "AcDbPoint") (cons 10 p) (xyzt:tag lot line))))
(defun xyzt:bump (key counts) (xyzt:put key (1+ (cond ((xyzt:get key counts)) (T 0))) counts))
(defun xyzt:csv-quote (s / i out ch)
  (setq i 1 out "\"")
  (while (<= i (strlen s))
    (setq ch (substr s i 1) out (strcat out (if (= ch "\"") "\"\"" ch)) i (1+ i)))
  (strcat out "\""))
(defun xyzt:log (line reason s)
  (if *xyzt:log* (write-line (strcat (itoa line) ";" reason ";" (xyzt:csv-quote s)) *xyzt:log*)))
(defun xyzt:emit (p ln lot classes cfg / index en c)
  (setq index (xyzt:class-index (caddr p) classes (xyzt:get "outside" cfg)))
  (if (null index)
    (progn (setq *xyzt:counts* (xyzt:bump "FUERA_CLASES" *xyzt:counts*))
      (xyzt:log ln "FUERA_CLASES" (vl-prin1-to-string p)))
    (progn
      (setq c (nth index classes) en (xyzt:point p ln lot (car c)))
      (if (not en) (xyzt:fail (strcat "Fallo creando POINT en linea " (itoa ln))))
      (if (= (xyzt:get "labels" cfg) "1") (xyz:label p ln lot c cfg))
      (setq *xyzt:imported* (1+ *xyzt:imported*)
            *xyzt:classcounts* (xyzt:bump (car c) *xyzt:classcounts*)
            *xyzt:importstats* (xyzt:stat-add *xyzt:importstats* p)))))
(defun xyzt:import (cfg poly sep classes lot / f s ln p reason mode n grid near dup keys key old val eligible)
  (setq mode (atoi (xyzt:get "reduce" cfg))
        grid (if (member mode '(2 3 4)) (xyzt:new-dict) nil)
        near (if (= mode 5) (xyzt:new-dict) nil)
        dup (if (/= (xyzt:get "duplicates" cfg) "0") (xyzt:new-dict) nil)
        f (xyzt:open-input (xyzt:get "file" cfg)) ln 0 eligible 0 keys nil)
  (setq *xyzt:counts* nil *xyzt:classcounts* nil *xyzt:imported* 0 *xyzt:importstats* (xyzt:empty-stat))
  (while (setq s (xyzt:read-line f))
    (setq ln (1+ ln))
    (cond
      ((or (<= ln (atoi (xyzt:get "skip" cfg))) (xyzt:comment s) (xyzt:header s cfg sep))
        (setq *xyzt:counts* (xyzt:bump "OMITIDAS" *xyzt:counts*)))
      ((not (setq p (xyzt:line s cfg sep)))
        (setq *xyzt:counts* (xyzt:bump "INVALIDAS" *xyzt:counts*)) (xyzt:log ln "XYZ_INVALIDO" s))
      ((setq reason (xyzt:filter-reason p cfg poly))
        (setq *xyzt:counts* (xyzt:bump reason *xyzt:counts*)) (xyzt:log ln reason s))
      ((and (= (xyzt:get "outside" cfg) "0") (null (xyzt:class-index (caddr p) classes "0")))
        (setq *xyzt:counts* (xyzt:bump "FUERA_CLASES" *xyzt:counts*)) (xyzt:log ln "FUERA_CLASES" s))
      ((and dup (xyzt:duplicate dup p cfg))
        (setq *xyzt:counts* (xyzt:bump "DUPLICADOS" *xyzt:counts*)) (xyzt:log ln "DUPLICADO" s))
      (T
        (setq eligible (1+ eligible))
        (cond
          ((and (= mode 1) (/= (rem (1- eligible) (atoi (xyzt:get "every" cfg))) 0))
            (setq *xyzt:counts* (xyzt:bump "REDUCIDOS" *xyzt:counts*)) (xyzt:log ln "CADA_N" s))
          ((member mode '(2 3 4))
            (setq key (xyzt:cellkey (xyzt:cell p (xyzt:get 'v-spacing cfg)))
                  old (xyzt:dict-get grid key) val (list p ln))
            (if (not old) (setq keys (cons key keys))
              (progn
                (setq *xyzt:counts* (xyzt:bump "REDUCIDOS" *xyzt:counts*))
                (if (xyzt:grid-better val old mode)
                  (xyzt:log (cadr old) "CELDA_REEMPLAZADO" (vl-prin1-to-string (car old)))
                  (xyzt:log ln "CELDA_DESCARTADO" s))))
            (if (xyzt:grid-better val old mode) (xyzt:dict-set grid key val)))
          ((and (= mode 5) (xyzt:near near p (xyzt:get 'v-spacing cfg) 2))
            (setq *xyzt:counts* (xyzt:bump "REDUCIDOS" *xyzt:counts*)) (xyzt:log ln "DISTANCIA_XY" s))
          (T (if near (xyzt:store-near near p (xyzt:get 'v-spacing cfg) 2))
             (xyzt:emit p ln lot classes cfg)))))
    (if (= 0 (rem ln 10000))
      (princ (strcat "\rIXYZ: " (itoa ln) " lineas | " (itoa *xyzt:imported*) " puntos creados..."))))
  (xyzt:close-input)
  (if grid
    (foreach key (reverse keys)
      (setq val (xyzt:dict-get grid key)) (xyzt:emit (car val) (cadr val) lot classes cfg)))
  (setq *xyzt:counts* (xyzt:put "LINEAS" ln *xyzt:counts*)
        *xyzt:counts* (xyzt:put "IMPORTADOS" *xyzt:imported* *xyzt:counts*)))

;;; Leyenda: bloque 2D en plano WCS XY a Z=0; punto de insercion del UCS a WCS.
;;; SOLID relleno y texto neutro para legibilidad. Todo etiquetado por lote.
(defun xyzt:text (p h s layer lot)
  (xyzt:make (list '(0 . "TEXT") '(100 . "AcDbEntity") (cons 8 layer) '(62 . 7)
    '(100 . "AcDbText") (cons 10 p) (cons 40 h) (cons 1 s) '(7 . "Standard")
    (xyzt:tag lot 0))))
(defun xyzt:legend (classes cfg lot base / name h x y info color count)
  (setq name (strcat (xyzt:get "prefix" cfg) "_" lot "_LEYENDA")
        h (xyzt:get 'v-height cfg) x (car base) y (cadr base))
  (xyzt:layer name '(255 255 255))
  (xyzt:text (list x y 0.0) (* h 1.25) (strcat "XYZ-Tools " lot " | COTAS (m)") name lot)
  (setq y (- y (* h 2.2)))
  (xyzt:text (list x y 0.0) h (strcat "Ref. vertical: " (xyzt:get "ref" cfg)) name lot)
  (setq y (- y (* h 2.0)))
  (xyzt:text (list x y 0.0) h (strcat "Sistema: " (xyzt:get "crs" cfg)) name lot)
  (setq y (- y (* h 2.0)))
  (foreach info (reverse classes)
    (setq color (xyzt:tc (nth 3 info)) count (cond ((xyzt:get (car info) *xyzt:classcounts*)) (T 0)))
    (xyzt:make (list '(0 . "SOLID") '(100 . "AcDbEntity") (cons 8 name) (cons 420 color)
      '(100 . "AcDbTrace") (cons 10 (list x y 0.0)) (cons 11 (list (+ x (* 2 h)) y 0.0))
      (cons 12 (list x (+ y h) 0.0)) (cons 13 (list (+ x (* 2 h)) (+ y h) 0.0))
      (xyzt:tag lot 0)))
    (xyzt:text (list (+ x (* 3 h)) y 0.0) h
      (strcat (xyzt:class-label info)
        " | " (itoa count) " pts | " (rtos (xyzt:percent count *xyzt:imported*) 2 2) "%") name lot)
    (setq y (- y (* h 1.8)))) name)
(defun xyzt:report (path cfg sep lot classes stats seconds / f info n pair sel)
  (setq f (open path "w"))
  (if (not f) (xyzt:fail "No se pudo crear el CSV de resultados."))
  (setq *xyzt:out* f)
  (write-line "Seccion;Dato;Valor;Z_min;Z_max;Color_RGB;Puntos;Porcentaje" f)
  (foreach pair (list (cons "Version" *xyzt:version*) (cons "Lote" lot)
      (cons "Archivo" (xyzt:get "file" cfg)) (cons "Referencia_vertical" (xyzt:get "ref" cfg))
      (cons "Sistema_declarado" (xyzt:get "crs" cfg)) (cons "Salida" "Metros WCS; no reproyectado")
      (cons "Separador" (if (= sep (chr 9)) "TAB" sep)) (cons "Segundos" (xyzt:nstr seconds)))
    (write-line (strcat "METADATO;" (car pair) ";" (xyzt:csv-quote (cdr pair))) f))
  (foreach pair cfg
    (if (eq (type (car pair)) 'STR)
      (write-line (strcat "CONFIG;" (car pair) ";" (xyzt:csv-quote (cdr pair))) f)))
  (if *xyzt:polygon*
    (write-line (strcat "METADATO;Poligono_WCS;" (xyzt:csv-quote (xyzt:serialize *xyzt:polygon*))) f))
  (foreach pair *xyzt:counts*
    (write-line (strcat "CONTADOR;" (car pair) ";" (itoa (cdr pair))) f))
  (foreach info classes
    (setq n (cond ((xyzt:get (car info) *xyzt:classcounts*)) (T 0)))
    (write-line (strcat "CLASE;" (xyzt:csv-quote (car info)) ";;" (xyzt:class-bound info 1) ";"
      (xyzt:class-bound info 2) ";" (xyzt:hex (nth 3 info)) ";" (itoa n) ";"
      (xyzt:nstr (xyzt:percent n *xyzt:imported*))) f))
  (foreach pair (list (cons "ARCHIVO" (xyzt:get 'raw stats)) (cons "FILTROS" (xyzt:get 'eligible stats))
                     (cons "IMPORTADOS" *xyzt:importstats*))
    (setq sel (cdr pair))
    (if (> (car (car sel)) 0)
      (progn
        (write-line (strcat "ESTADISTICA;" (car pair) "_Z_MEDIA;" (xyzt:nstr (cadr (car sel)))) f)
        (write-line (strcat "ESTADISTICA;" (car pair) "_Z_DESV_MUESTRAL;" (xyzt:nstr (xyzt:std sel))) f)
        (write-line (strcat "ESTADISTICA;" (car pair) "_XYZ_MIN;" (xyzt:csv-quote (xyzt:serialize (nth 3 sel)))) f)
        (write-line (strcat "ESTADISTICA;" (car pair) "_XYZ_MAX;" (xyzt:csv-quote (xyzt:serialize (nth 4 sel)))) f))))
  (close f) (setq *xyzt:out* nil))

;;; Aislamiento reversible, almacenado por documento en memoria de sesion.
(defun xyzt:doc-key () (strcat (getvar "DWGPREFIX") (getvar "DWGNAME")))
(defun xyzt:isolate (names / doc layers ly name snapshot key result)
  (setq key (xyzt:doc-key) doc (vla-get-ActiveDocument (vlax-get-acad-object))
        layers (vla-get-Layers doc) snapshot nil)
  (vlax-for ly layers
    (setq name (vla-get-Name ly))
    (setq snapshot (cons (cons name (vla-get-LayerOn ly)) snapshot)))
  (if (not (assoc key *xyzt:layerstates*))
    (setq *xyzt:layerstates* (cons (cons key snapshot) *xyzt:layerstates*)))
  (vlax-for ly layers
    (setq name (vla-get-Name ly))
    (setq result (vl-catch-all-apply 'vla-put-LayerOn
      (list ly (if (or (member name names) (= name (getvar "CLAYER"))) :vlax-true :vlax-false))))
    (if (vl-catch-all-error-p result) (princ (strcat "\nNo se cambio visibilidad: " name))))
  (princ "\nVisibilidad guardada. XYZRESTAURAR restaura las capas en esta sesion."))
(defun c:XYZRESTAURAR (/ key state doc layers pair ly res)
  (setq key (xyzt:doc-key) state (assoc key *xyzt:layerstates*))
  (if (not state) (princ "\nNo hay aislamiento XYZ-Tools pendiente en este documento.")
    (progn
      (setq doc (vla-get-ActiveDocument (vlax-get-acad-object)) layers (vla-get-Layers doc))
      (foreach pair (cdr state)
        (if (tblsearch "LAYER" (car pair))
          (progn
            (setq ly (vla-Item layers (car pair)))
            (setq res (vl-catch-all-apply 'vla-put-LayerOn (list ly (cdr pair))))
            (if (vl-catch-all-error-p res) (princ (strcat "\nNo restaurada: " (car pair)))))))
      (setq *xyzt:layerstates* (vl-remove state *xyzt:layerstates*))
      (vla-Regen doc 1) (princ "\nVisibilidad restaurada."))) (princ))
(defun xyzt:release () (setq *xyzt:objects* nil))
(defun xyzt:cleanup (/ file)
  (xyzt:close-input)
  (if *xyzt:out* (progn (close *xyzt:out*) (setq *xyzt:out* nil)))
  (if *xyzt:log* (progn (close *xyzt:log*) (setq *xyzt:log* nil)))
  (xyzt:release)
  (foreach file *xyz:workfiles* (if (findfile file) (vl-file-delete file)))
  (setq *xyz:workfiles* nil)
  (if (and *xyzt:dclid* (>= *xyzt:dclid* 0)) (unload_dialog *xyzt:dclid*))
  (setq *xyzt:dclid* nil)
  (if *xyzt:dclfile* (vl-file-delete *xyzt:dclfile*))
  (setq *xyzt:dclfile* nil))
(defun xyzt:rollback (lot / en name obj root)
  (if lot
    (progn
      (foreach en (xyzt:lot-selection lot) (vl-catch-all-apply 'entdel (list en)))
      (if (setq root (dictsearch (namedobjdict) "IXYZ7_LOTES"))
        (if (setq en (dictremove (cdr (assoc -1 root)) lot)) (entdel en)))))
  (foreach en *xyzt:deleted* (vl-catch-all-apply 'entdel (list en)))
  (foreach name *xyzt:newlayers*
    (if (tblsearch "LAYER" name)
      (progn
        (setq obj (vla-Item (vla-get-Layers (vla-get-ActiveDocument (vlax-get-acad-object))) name))
        (vl-catch-all-apply 'vla-Delete (list obj)))))
  (setq *xyzt:deleted* nil *xyzt:newlayers* nil))

;;; Interfaz: todos los getfiled/getpoint/entsel se realizan FUERA de callbacks.
(defun xyzt:ui-save (/ key)
  (foreach key xyzt:keys (setq *xyzt:ui* (xyzt:put key (get_tile key) *xyzt:ui*))))
(defun xyzt:ui-exit (code) (xyzt:ui-save) (done_dialog code))
(defun xyzt:fill-popup (key values / s)
  (start_list key) (foreach s values (add_list s)) (end_list))
(defun xyzt:dialog (/ key result)
  (if (not (new_dialog "XYZ_MAIN" *xyzt:dclid*)) (xyzt:fail "No se pudo iniciar la interfaz integrada."))
  (xyzt:fill-popup "sep" '("Automatico" "Espacios/TAB" "TAB" "Punto y coma" "Coma"))
  (xyzt:fill-popup "decimal" '("Punto decimal" "Coma decimal"))
  (xyzt:fill-popup "units" '("Entrada en metros" "Entrada en pies internacionales" "Entrada en milimetros"))
  (xyzt:fill-popup "zmode" '("Conservar signo Z" "Profundidad positiva -> elevacion (-Z)"))
  (xyzt:fill-popup "palette" '("CCN topografica" "CCN batimetrica"))
  (xyzt:fill-popup "classmode" '("Automatico redondeado (clases aprox.)" "Intervalo fijo @ (m)" "Limites comunes redondeados"))
  (xyzt:fill-popup "outside" '("Excluir fuera de limites comunes" "Incluir en clases << y >>"))
  (xyzt:fill-popup "reduce" '("Sin reduccion" "Uno de cada N" "Celda: primer punto" "Celda: mas somero (Z mayor)" "Celda: mas profundo (Z menor)" "Distancia minima XY"))
  (xyzt:fill-popup "duplicates" '("Conservar duplicados" "Eliminar XYZ exactamente iguales" "Eliminar cercanos por distancia 3D"))
  (foreach key xyzt:keys (set_tile key (xyzt:get key *xyzt:ui*)))
  (set_tile "polygon_status" (if *xyzt:polygon* (strcat "Poligono: " (itoa (length *xyzt:polygon*)) " vertices") "Poligono: ninguno"))
  (set_tile "replace_status" (if *xyzt:replace* (strcat "Reemplazar solo lote " *xyzt:replace*) "Modo: agregar lote nuevo"))
  (set_tile "status" *xyzt:status*)
  (action_tile "file_button" "(xyzt:ui-exit 2)")
  (action_tile "poly_button" "(xyzt:ui-exit 3)")
  (action_tile "analyze" "(xyzt:ui-exit 4)")
  (action_tile "preview" "(xyzt:ui-exit 5)")
  (action_tile "replace_button" "(xyzt:ui-exit 6)")
  (action_tile "help" "(xyzt:ui-exit 7)")
  (action_tile "out_button" "(xyzt:ui-exit 8)")
  (action_tile "clear_poly" "(setq *xyzt:polygon* nil)(set_tile \"polygon_status\" \"Poligono: ninguno\")")
  (action_tile "clear_replace" "(setq *xyzt:replace* nil)(set_tile \"replace_status\" \"Modo: agregar lote nuevo\")")
  (action_tile "process_button" "(xyzt:ui-exit 9)")
  (action_tile "merge_button" "(xyzt:ui-exit 10)")
  (action_tile "labels_button" "(xyzt:ui-exit 11)")
  (action_tile "pointtools_button" "(xyzt:ui-exit 12)")
  (action_tile "export_button" "(xyzt:ui-exit 13)")
  (action_tile "accept" "(xyzt:ui-exit 1)")
  (action_tile "cancel" "(xyzt:ui-exit 0)")
  (start_dialog))
(defun xyzt:preview (cfg sep / f s ln shown p text)
  (setq f (xyzt:open-input (xyzt:get "file" cfg)) ln 0 shown 0 text "Vista previa (coordenadas de salida en metros):\n")
  (while (and (< shown 8) (setq s (xyzt:read-line f)))
    (setq ln (1+ ln))
    (if (> ln (atoi (xyzt:get "skip" cfg)))
      (progn
        (setq shown (1+ shown) p (xyzt:line s cfg sep))
        (setq text (strcat text "\nL" (itoa ln) " " (substr s 1 90) "\n -> "
          (if p (strcat (xyzt:nstr (car p)) " | " (xyzt:nstr (cadr p)) " | " (xyzt:nstr (caddr p))) "No es una fila XYZ valida"))))))
  (xyzt:close-input) (alert text))
(defun xyzt:select-lot (/ sel lot)
  (setq sel (entsel "\nSeleccione un punto o leyenda creado por XYZ-Tools 7: "))
  (if sel
    (if (setq lot (xyzt:lot-of (car sel))) lot
      (xyzt:fail "El objeto no pertenece a un lote XYZ-Tools 7. Los objetos antiguos se conservan."))))
(defun c:XYZAYUDA ()
  (alert (strcat "XYZ-Tools " *xyzt:version* " - Guia rapida\n\n"
    "XYZ / IXYZ: importar. Botones Procesar/Unir abren esos modos.\n"
    "P-Z: panel Pantalla/Archivo. IZ: invierte puntos POINT seleccionados.\n"
    "OZ: mueve seleccion en Z mundial; ZM: estadisticas de puntos.\n"
    "EXYZ / XYZEXPORTAR: exportar seleccion POINT. No modifica el dibujo.\n"
    "Colores: intervalos redondeados; modo fijo admite @0.50, @1.00, etc.\n"
    "La simbologia se ubica despues de importar y mostrar la nube.\n"
    "XYZU: alias de union. Procesar incluye Z minima/maxima de archivo.\n"
    "N/ID X Y Z: elegir formato o columnas 2,3,4. No se adivinan columnas.\n"
    "IZ/OZ cambian solo objetos seleccionados. Revisar etiquetas y leyendas.\n"
    "PZ: procesar directo. XYZUNIR: unir directo. Etiquetas: boton dedicado.\n"
    "Procesar: invierte Z, offset, rangos o elimina un rango.\n"
    "Conserva X/Y y campos adicionales; normaliza separadores/comillas.\n"
    "Rangos ordenados [min,max); ultimo incluye max. No superposiciones.\n"
    "Unir: salida XYZ normalizada; mismas unidades y sistema en las fuentes.\n"
    "Decimales -1 conserva hasta 16 decimales, sin ceros de relleno.\n"
    "Nunca sobrescribe originales; agrega consecutivo si existe el destino.\n"
    "1. Archivo, separador, decimal y columnas (desde 1).\n"
    "2. Unidades de entrada. Salida siempre en METROS y WCS.\n"
    "3. Z: conservar o negar; despues sumar Delta Z en METROS.\n"
    "   Ejemplo profundidad d y agua H: Z=H-d (Delta Z=H).\n"
    "   Datos HYPACK ya reducidos: conservar Z; Delta Z=0.\n"
    "4. Declarar sistema y referencia vertical. NO reproyecta.\n"
    "5. Filtros y clases usan coordenadas YA convertidas.\n"
    "6. Vista previa y Analizar. Importar vuelve a analizar siempre.\n\n"
    "CELDAS: ancladas al origen WCS; cada celda conserva un punto real.\n"
    "Mas somero=Z mayor; profundo=Z menor (elevaciones finales).\n"
    "Distancia minima y Cada N dependen del orden de entrada.\n"
    "Duplicados: XYZ exacto o distancia 3D menor que tolerancia.\n"
    "Se filtra antes de reducir; limites de clases comunes se aplican primero.\n"
    "CSV: separador ; y punto decimal. Importar en Excel indicando ambos.\n"
    "Resultados y descartes llevan ID de lote, nunca sobrescriben otros.\n\n"
    "XYZLOTES: ver lotes. XYZBORRAR: borrar solo lote seleccionado.\n"
    "XYZRESTAURAR: visibilidad anterior (durante esta sesion/documento).\n"
    "XYZTEST: comprobaciones de funciones puras. U: deshacer importacion.\n"
    "El respaldo opcional es del XYZ, no del DWG.\n"
    "Trabajar en un dibujo en METROS, desde Modelo. No cambia INSUNITS.\n"
    "Leyenda en plano XY mundial a Z=0.\n"
    "Celdas y tolerancias: minimo 0.000001 m; clases: maximo 100.\n"
    "Numeros de ajustes aceptan punto o coma. Archivo segun decimal elegido.\n"
    "Coordenadas admitidas: |X,Y|<=1e9; |Z|<=1e7 metros.\n"
    "No elimina atipicos automaticamente ni procesa sonar crudo.\n"
    "Integracion AutoCAD/ZWCAD: pendiente de validacion en el equipo.")) (princ))
(defun c:XYZLOTES (/ root pair data key count)
  (setq root (dictsearch (namedobjdict) "IXYZ7_LOTES") count 0)
  (if root
    (progn
      (setq root (cdr (assoc -1 root)))
      (foreach pair (entget root)
        (if (= (car pair) 3)
          (progn
            (setq key (cdr pair) data (dictsearch root key) count (1+ count))
            (princ (strcat "\n" key))
            (foreach pair data
              (if (and (= (car pair) 1)
                 (or (wcmatch (cdr pair) "FUENTE=*") (wcmatch (cdr pair) "IMPORTADOS=*")))
                (princ (strcat " | " (cdr pair))))))))))
  (princ (strcat "\nLotes registrados: " (itoa count))) (princ))
(defun c:XYZBORRAR (/ *error* lot en doc mark deleted root record)
  (setq doc (vla-get-ActiveDocument (vlax-get-acad-object)) deleted nil mark nil *xyzt:failure* nil)
  (defun *error* (msg)
    (setq msg (if *xyzt:failure* *xyzt:failure* msg) *xyzt:failure* nil)
    (foreach en deleted (vl-catch-all-apply 'entdel (list en)))
    (if mark (vl-catch-all-apply 'vla-EndUndoMark (list doc)))
    (princ (strcat "\nXYZBORRAR: " msg)) (princ))
  (if (setq lot (xyzt:select-lot))
    (progn
      (vla-StartUndoMark doc) (setq mark T)
      (foreach en (xyzt:lot-selection lot)
        (if (entdel en) (setq deleted (cons en deleted)) (xyzt:fail "No se pudo borrar el lote completo.")))
      ;; Se mantiene XRECORD como historial del lote borrado.
      (vla-EndUndoMark doc) (setq mark nil deleted nil)
      (princ (strcat "\nLote " lot " borrado. Historial conservado; U permite deshacer.")))) (princ))

(defun xyzt:run (/ code validated res path cfg sep stats classes lot doc mark oldcm olddz
                   oldpd legendbase legendname reportpath logpath backupdir backuppath
                   outputdir start seconds en pair filesok done source-stamp newstamp tmp entry process-result)
  (setq oldcm (getvar "CMDECHO") olddz (getvar "DIMZIN") oldpd (getvar "PDSIZE")
        doc (vla-get-ActiveDocument (vlax-get-acad-object)) mark nil lot nil done nil
        *xyzt:in* nil *xyzt:out* nil *xyzt:log* nil *xyzt:objects* nil *xyzt:newlayers* nil *xyzt:deleted* nil
        *xyzt:polygon* nil *xyzt:replace* nil *xyzt:status* "Vista previa -> Analizar -> Importar")

  (if (not *xyzt:lastcfg*) (setq *xyzt:lastcfg* (xyzt:defaults)))
  (setq *xyzt:ui* *xyzt:lastcfg*)
  (setvar "DIMZIN" 0)
  (xyzt:make-dcl)
  (setq *xyzt:dclid* (load_dialog *xyzt:dclfile*))
  (if (< *xyzt:dclid* 0) (xyzt:fail "No se pudo cargar DCL temporal."))
  (setq entry *xyz:entry* *xyz:entry* nil code -1)
  (if entry
    (progn
      (setq process-result (cond ((= entry "export") (xyz:export-screen) nil) ((= entry "pointtools") (xyz:pointtools-flow)) (T (xyz:process-flow (= entry "merge")))))
      (if process-result
        (setq cfg (xyzt:validate *xyzt:ui*) sep (xyzt:detect cfg) stats (xyzt:analyze cfg nil sep)
              source-stamp (xyz:signature (xyzt:get "file" cfg)) code 1)
        (setq code 0))))
  (while (and (/= code 0) (/= code 1))
    (setq code (xyzt:dialog))
    (cond
      ((= code 2)
        (setq path (getfiled "Archivo XYZ / TXT / CSV" (xyzt:get "file" *xyzt:ui*) "xyz;txt;csv;asc" 0))
        (if path (setq *xyzt:ui* (xyzt:put "file" path *xyzt:ui*) *xyzt:status* "Archivo cambiado: vuelva a analizar.")))
      ((= code 3)
        (setq res (xyzt:try 'xyzt:polygon nil))
        (if (vl-catch-all-error-p res) (alert (xyzt:errmsg res)) (setq *xyzt:polygon* res)))
      ((member code '(1 4 5))
        (setq res (xyzt:try 'xyzt:validate (list *xyzt:ui*)))
        (if (vl-catch-all-error-p res) (progn (alert (xyzt:errmsg res)) (setq code -1))
          (progn
            (setq cfg res source-stamp (list (vl-file-size (xyzt:get "file" cfg)) (vl-file-systime (xyzt:get "file" cfg)))
                  res (xyzt:try 'xyzt:detect (list cfg)))
            (if (vl-catch-all-error-p res)
              (progn (xyzt:close-input) (alert (xyzt:errmsg res)) (setq code -1))
              (progn
                (setq sep res)
                (if (= code 5)
                  (setq res (xyzt:try 'xyzt:preview (list cfg sep)))
                  (progn
                    (setq res (xyzt:try 'xyzt:analyze (list cfg *xyzt:polygon* sep)))
                    (if (not (vl-catch-all-error-p res))
                      (progn
                        (setq stats res *xyzt:status* (strcat "Ultimo analisis: " (itoa (xyzt:get 'lines stats)) " filas. Importar recalcula con los ajustes actuales."))
                        (if (= code 4) (alert (xyzt:stats-text stats)))))))
                (if (vl-catch-all-error-p res)
                  (progn (xyzt:close-input) (alert (xyzt:errmsg res)) (setq code -1))
                (if (and (= code 1) (= 0 (car (car (xyzt:get 'eligible stats)))))
                  (progn (alert "No hay puntos dentro de los filtros.") (setq code -1)))))))))
      ((= code 6)
        (setq res (xyzt:try 'xyzt:select-lot nil))
        (if (vl-catch-all-error-p res) (alert (xyzt:errmsg res)) (setq *xyzt:replace* res)))
      ((member code '(9 10))
        (setq process-result (xyz:process-flow (= code 10)))
        (if process-result
          (setq cfg (xyzt:validate *xyzt:ui*) sep (xyzt:detect cfg) stats (xyzt:analyze cfg *xyzt:polygon* sep)
                source-stamp (xyz:signature (xyzt:get "file" cfg)) code 1)))
      ((= code 13) (xyz:export-screen))
      ((= code 12)
        (setq process-result (xyz:pointtools-flow))
        (if process-result
          (setq cfg (xyzt:validate *xyzt:ui*) sep (xyzt:detect cfg) stats (xyzt:analyze cfg *xyzt:polygon* sep)
                source-stamp (xyz:signature (xyzt:get "file" cfg)) code 1)))
      ((= code 11) (xyz:labels-dialog))
      ((= code 7) (c:XYZAYUDA))
      ((= code 8)
        (setq path (getfiled "Elija carpeta de salida (nombre solo orientativo)" "IXYZ.csv" "csv" 1))
        (if path (setq *xyzt:ui* (xyzt:put "outdir" (vl-filename-directory path) *xyzt:ui*))))))
  (setq *xyzt:lastcfg* *xyzt:ui*)
  (if (= code 1)
    (progn
      (if (not (= (getvar "TILEMODE") 1)) (xyzt:fail "Para importar puntos, active la pestana Modelo."))
      (if (= 0 (logand 1 (getvar "UNDOCTL"))) (xyzt:fail "Active DESHACER antes de importar."))
      (if (= 0 (car (car (xyzt:get 'eligible stats)))) (xyzt:fail "Ningun punto dentro de filtros de importacion."))
      (setq *xyzt:active-lot* nil lot (xyzt:lot-id) *xyzt:active-lot* lot
            classes (xyzt:classes cfg stats lot))
      ;; Si el archivo cambia entre analisis y lectura se aborta sin reemplazar lote.
      (if (not (equal source-stamp (list (vl-file-size (xyzt:get "file" cfg)) (vl-file-systime (xyzt:get "file" cfg)))))
        (xyzt:fail "El archivo cambio durante el analisis. Repita con archivo estable."))
      ;; Validar servicios espaciales antes de crear objetos.
      (if (or (>= (atoi (xyzt:get "reduce" cfg)) 2) (/= (xyzt:get "duplicates" cfg) "0"))
        (progn (xyzt:new-dict) (xyzt:release)))
      (setq outputdir (if (= (xyzt:get "outdir" cfg) "") (vl-filename-directory (xyzt:get "file" cfg)) (xyzt:get "outdir" cfg))
            reportpath (strcat outputdir "\\" (vl-filename-base (xyzt:get "file" cfg)) "_" lot "_resultados.csv")
            logpath (strcat outputdir "\\" (vl-filename-base (xyzt:get "file" cfg)) "_" lot "_descartes.csv"))
      (if (= (xyzt:get "csv" cfg) "1")
        (progn
          (if (or (findfile logpath) (findfile reportpath)) (xyzt:fail "Ya existe un reporte con ese ID; no se sobrescribio."))
          (setq *xyzt:report-files* (list logpath reportpath))
          (setq *xyzt:log* (open logpath "w"))
          (if (not *xyzt:log*) (xyzt:fail "No se puede escribir CSV. Elija otra carpeta o desactive CSV."))
          (write-line "Linea;Motivo;Contenido" *xyzt:log*)))
      (if (= (xyzt:get "backup" cfg) "1")
        (progn
          (setq backuppath (strcat outputdir "\\" (vl-filename-base (xyzt:get "file" cfg)) "_" lot "_FUENTE"
                             (vl-filename-extension (xyzt:get "file" cfg))))
          (if (not (vl-file-copy (xyzt:get "file" cfg) backuppath)) (xyzt:fail "Fallo el respaldo del archivo fuente."))
          (princ (strcat "\nRespaldo fuente: " backuppath))))
      (setq legendbase nil)
      (setvar "CMDECHO" 0) (setvar "DIMZIN" 0)
      (vla-StartUndoMark doc) (setq *xyzt:undo* T)
      (regapp "IXYZ7")
      (foreach pair classes (xyzt:layer (car pair) (nth 3 pair)))
      (setq *xyz:label-layer* nil)
      (if (and (= (xyzt:get "labels" cfg) "1") (= (xyzt:get "labelone" cfg) "1"))
        (progn
          (setq *xyz:label-layer* (strcat (xyzt:get "labellayer" cfg) "_" lot))
          (xyzt:layer *xyz:label-layer* '(255 255 255))))
      (setq start (getvar "MILLISECS"))
      (xyzt:import cfg *xyzt:polygon* sep classes lot)
      (setq seconds (/ (- (getvar "MILLISECS") start) 1000.0))
      (if (< seconds 0.0) (setq seconds 0.0))
      (if *xyzt:log* (progn (close *xyzt:log*) (setq *xyzt:log* nil)))
      (setq newstamp (list (vl-file-size (xyzt:get "file" cfg)) (vl-file-systime (xyzt:get "file" cfg))))
      (if (not (equal source-stamp newstamp)) (xyzt:fail "El archivo cambio durante la importacion. Repita con archivo estable."))
      (if (= *xyzt:imported* 0) (xyzt:fail "Ningun punto creado. El lote anterior se conserva."))
      ;; Mostrar la nube ANTES de pedir la ubicacion de la simbologia.
      (if (= (xyzt:get "legend" cfg) "1")
        (progn
          (vl-catch-all-apply 'vla-ZoomWindow
            (list (vlax-get-acad-object)
              (vlax-3d-point (mapcar '- (nth 3 *xyzt:importstats*) '(1.0 1.0 0.0)))
              (vlax-3d-point (mapcar '+ (nth 4 *xyzt:importstats*) '(1.0 1.0 0.0)))))
          (vla-Regen doc 1) (redraw)
          (princ "\nNube importada y mostrada. Ubique ahora la simbologia.")
          (setq res (xyzt:try 'getpoint (list "\nInsercion de simbologia (Enter/Esc: omitir y conservar puntos): ")))
          (if (not (vl-catch-all-error-p res))
            (if res (setq legendbase (trans res 1 0)))
            (progn (setq *xyzt:failure* nil) (princ "\nSimbologia omitida; los puntos se conservan.")))))
      (setq legendname (if legendbase (xyzt:legend classes cfg lot legendbase) nil))
      (xyzt:record lot cfg classes stats *xyzt:imported* *xyzt:counts*)
      (if (= (xyzt:get "csv" cfg) "1") (xyzt:report reportpath cfg sep lot classes stats seconds))
      (if *xyzt:replace*
        (foreach en (xyzt:lot-selection *xyzt:replace*)
          (if (entdel en) (setq *xyzt:deleted* (cons en *xyzt:deleted*))
            (xyzt:fail "No se pudo reemplazar el lote completo. Se restaura el anterior."))))
      (if (/= (xyzt:get 'v-pdsize cfg) 0.0) (setvar "PDSIZE" (xyzt:get 'v-pdsize cfg)))
      (vla-EndUndoMark doc) (setq *xyzt:undo* nil *xyzt:active-lot* nil *xyzt:deleted* nil *xyzt:newlayers* nil)
      (setq *xyzt:report-files* nil done T)
      ;; Operaciones visuales auxiliares no invalidan una importacion terminada.
      (if (and (= (xyzt:get "zoom" cfg) "1") (/= (xyzt:get "legend" cfg) "1"))
        (vl-catch-all-apply 'vla-ZoomWindow
          (list (vlax-get-acad-object)
            (vlax-3d-point (mapcar '- (nth 3 *xyzt:importstats*) '(1.0 1.0 0.0)))
            (vlax-3d-point (mapcar '+ (nth 4 *xyzt:importstats*) '(1.0 1.0 0.0))))))
      (if (= (xyzt:get "isolate" cfg) "1")
        (progn
          (setq res (vl-catch-all-apply 'xyzt:isolate (list (append (mapcar 'car classes) (if legendname (list legendname) nil) (if *xyz:label-layer* (list *xyz:label-layer*) nil)))))
          (if (vl-catch-all-error-p res) (princ "\nNo se completo aislamiento; los puntos se importaron."))))
      (vl-catch-all-apply 'vla-Regen (list doc 1))
      (princ (strcat "\nXYZ-Tools " *xyzt:version* " | Lote " lot " | " (itoa *xyzt:imported*) " puntos | " (rtos seconds 2 2) " s"))
      (foreach pair *xyzt:counts* (princ (strcat "\n  " (car pair) ": " (itoa (cdr pair)))))
      (if (= (xyzt:get "csv" cfg) "1") (princ (strcat "\nResultados: " reportpath "\nDescartes: " logpath)))
      (alert (strcat "Importacion terminada\nLote: " lot "\nPuntos: " (itoa *xyzt:imported*)
        "\nTiempo del motor: " (rtos seconds 2 2) " s\n\nU deshace los cambios del dibujo."
        (if (= (xyzt:get "csv" cfg) "1") (strcat "\nCSV: " reportpath) "")))))
  (xyzt:cleanup)
  (setvar "CMDECHO" oldcm) (setvar "DIMZIN" olddz)
  (princ))
(defun c:XYZ (/ *error* savedcm saveddz savedpd doc path)
  (setq savedcm (getvar "CMDECHO") saveddz (getvar "DIMZIN") savedpd (getvar "PDSIZE")
        doc (vla-get-ActiveDocument (vlax-get-acad-object))
        *xyzt:active-lot* nil *xyzt:undo* nil *xyzt:report-files* nil *xyzt:failure* nil *xyz:workfiles* nil
        *xyzt:in* nil *xyzt:out* nil *xyzt:log* nil *xyzt:dclid* nil *xyzt:dclfile* nil
        *xyzt:objects* nil *xyzt:newlayers* nil *xyzt:deleted* nil)
  (defun *error* (msg)
    (setq msg (if *xyzt:failure* *xyzt:failure* msg) *xyzt:failure* nil)
    (xyzt:cleanup)
    (if *xyzt:active-lot* (xyzt:rollback *xyzt:active-lot*))
    (if *xyzt:undo* (vl-catch-all-apply 'vla-EndUndoMark (list doc)))
    (foreach path *xyzt:report-files* (if (findfile path) (vl-file-delete path)))
    (setvar "CMDECHO" savedcm) (setvar "DIMZIN" saveddz) (setvar "PDSIZE" savedpd)
    (setq *xyzt:undo* nil *xyzt:active-lot* nil *xyzt:report-files* nil)
    (princ (strcat "\nXYZ-Tools detenido: " (if msg msg "sin mensaje") "\nSe retiraron los objetos del lote incompleto, si los habia."))
    (princ))
  (xyzt:run) (princ))

(defun xyzt:rgb-ccn (indice total batimetria / escala ratio pos-frac pos-entera c1 c2 r g b)
  (setq escala '(
      (36 18 0) (100 50 0) (150 0 0) (255 0 0) (255 71 26)
      (255 100 0) (255 150 0) (255 255 0) (10 208 6) (6 147 44)
      (10 214 156) (0 200 255) (0 100 255) (0 0 255) (26 21 157)
      (16 13 99) (11 9 68)))
  (if batimetria (setq escala (reverse escala)))
  (if (<= total 1)
    (setq ratio 0.0)
    (setq ratio (/ (float (1- indice)) (float (1- total))))
  )
  (setq pos-frac (* ratio (1- (length escala))))
  (setq pos-entera (fix pos-frac))
  (if (>= pos-entera (1- (length escala)))
    (setq pos-entera (1- (length escala)))
  )
  (if (= pos-entera (1- (length escala)))
    (nth pos-entera escala)
    (progn
      (setq c1 (nth pos-entera escala)
            c2 (nth (1+ pos-entera) escala)
            pos-frac (- pos-frac pos-entera))
      (setq r (fix (+ (car c1) (* pos-frac (- (car c2) (car c1))))))
      (setq g (fix (+ (cadr c1) (* pos-frac (- (cadr c2) (cadr c1))))))
      (setq b (fix (+ (caddr c1) (* pos-frac (- (caddr c2) (caddr c1))))))
      (list (max 0 (min 255 r)) (max 0 (min 255 g)) (max 0 (min 255 b)))
    )
  )
)

(defun xyzt:make-dcl (/ f s)
  (setq *xyzt:dclfile* (vl-filename-mktemp "xyztools_" nil ".dcl"))
  (if (not (setq f (open *xyzt:dclfile* "w"))) (xyzt:fail "No se pudo escribir DCL temporal."))
  (setq *xyzt:out* f)
  (write-line "XYZ_MAIN : dialog { label=\"XYZ-Tools 2.6.2 - Importar, Procesar y Unir\";:row {:button {key=\"process_button\";label=\"Procesar archivo Z...\";}:button {key=\"merge_button\";label=\"Unir archivos...\";}:button {key=\"export_button\";label=\"Exportar puntos...\";}:button {key=\"labels_button\";label=\"Etiquetas...\";}:button {key=\"pointtools_button\";label=\"Operaciones en dibujo / P-Z...\";}}:row {:edit_box {key=\"file\";label=\"Archivo\";edit_width=85;edit_limit=1024;}:button {key=\"file_button\";label=\"Buscar...\";}}:row {:column {:boxed_column {label=\"1. Lectura\";:popup_list {key=\"sep\";label=\"Separador\";width=34;}:popup_list {key=\"decimal\";label=\"Decimales\";width=34;}:row {:edit_box {key=\"cx\";label=\"X col.\";edit_width=3;edit_limit=1024;}:edit_box {key=\"cy\";label=\"Y col.\";edit_width=3;edit_limit=1024;}:edit_box {key=\"cz\";label=\"Z col.\";edit_width=3;edit_limit=1024;}}:edit_box {key=\"skip\";label=\"Omitir primeras filas\";edit_width=5;edit_limit=1024;}:row {:button {key=\"preview\";label=\"Vista previa\";}:button {key=\"analyze\";label=\"Analizar\";}}}:boxed_column {label=\"2. Coordenadas\";:popup_list {key=\"units\";label=\"Unidades XYZ\";width=34;}:popup_list {key=\"zmode\";label=\"Interpretacion Z\";width=34;}:edit_box {key=\"dz\";label=\"Delta Z (m)\";edit_width=10;edit_limit=1024;}:edit_box {key=\"ref\";label=\"Ref. vertical\";edit_width=24;edit_limit=1024;}:edit_box {key=\"crs\";label=\"Sistema / zona\";edit_width=24;" f)
  (write-line "edit_limit=1024;}:text {label=\"Salida: METROS, coordenadas WCS.\";}:text {label=\"No reproyecta ni corrige sonar crudo.\";}}:boxed_column {label=\"Lote\";:text {key=\"replace_status\";width=34;}:row {:button {key=\"replace_button\";label=\"Elegir lote a reemplazar\";}:button {key=\"clear_replace\";label=\"Agregar nuevo\";}}}}:column {:boxed_column {label=\"3. Clasificacion\";:edit_box {key=\"prefix\";label=\"Prefijo\";edit_width=16;edit_limit=1024;}:popup_list {key=\"palette\";label=\"Colores\";width=34;}:popup_list {key=\"classmode\";label=\"Metodo\";width=34;}:row {:edit_box {key=\"classes\";label=\"Clases\";edit_width=4;edit_limit=1024;}:edit_box {key=\"step\";label=\"Intervalo (m)\";edit_width=7;edit_limit=1024;}}:row {:edit_box {key=\"base\";label=\"Desde (m)\";edit_width=8;edit_limit=1024;}:edit_box {key=\"top\";label=\"Hasta (m)\";edit_width=8;edit_limit=1024;}}:popup_list {key=\"outside\";label=\"Fuera de limites comunes\";width=34;}}:boxed_column {label=\"4. Filtros (metros de salida)\";:toggle {key=\"xyfilter\";label=\"Activar rectangulo XY\";}:row {:edit_box {key=\"xmin\";label=\"X min\";edit_width=10;edit_limit=1024;}:edit_box {key=\"xmax\";label=\"X max\";edit_width=10;edit_limit=1024;}}:row {:edit_box {key=\"ymin\";label=\"Y min\";edit_width=10;edit_limit=1024;}:edit_box {key=\"ymax\";label=\"Y max\";edit_width=10;edit_limit=1024;}}:toggle {key=\"zfilter\";label=\"Activar rango Z\";}:row {:edit_box {key=\"zmin\";label=\"Z min\";" f)
  (write-line "edit_width=10;edit_limit=1024;}:edit_box {key=\"zmax\";label=\"Z max\";edit_width=10;edit_limit=1024;}}:text {key=\"polygon_status\";width=34;}:row {:button {key=\"poly_button\";label=\"Elegir poligono\";}:button {key=\"clear_poly\";label=\"Quitar poligono\";}}}}:column {:boxed_column {label=\"5. Densidad\";:popup_list {key=\"reduce\";label=\"Reduccion\";width=34;}:row {:edit_box {key=\"every\";label=\"Cada N\";edit_width=6;edit_limit=1024;}:edit_box {key=\"spacing\";label=\"Celda / dist. (m)\";edit_width=7;edit_limit=1024;}}:popup_list {key=\"duplicates\";label=\"Duplicados\";width=34;}:edit_box {key=\"tol\";label=\"Tolerancia 3D (m)\";edit_width=8;edit_limit=1024;}:text {label=\"Somero = Z mayor; profundo = Z menor.\";}:text {label=\"Distancia minima: depende del orden.\";}}:boxed_column {label=\"6. Salida\";:toggle {key=\"legend\";label=\"Crear leyenda (insercion en Modelo)\";}:row {:edit_box {key=\"height\";label=\"Texto leyenda (m)\";edit_width=7;edit_limit=1024;}:edit_box {key=\"pdsize\";label=\"PDSIZE (0=conservar)\";edit_width=7;edit_limit=1024;}}:toggle {key=\"csv\";label=\"CSV de resultados y descartes\";}:toggle {key=\"backup\";label=\"Respaldar archivo XYZ fuente\";}:toggle {key=\"zoom\";label=\"Zoom al lote importado\";}:toggle {key=\"isolate\";label=\"Aislar lote y leyenda (reversible)\";}:edit_box {key=\"outdir\";label=\"Carpeta CSV / respaldo\";edit_width=27;edit_limit=1024;}:button {key=\"out_button\";label=\"Elegir carpeta...\";}}}}" f)
  (write-line ":text {key=\"status\";width=110;}:row {:button {key=\"help\";label=\"Ayuda / comandos\";}:spacer {width=25;}:button {key=\"accept\";label=\"Importar\";is_default=true;}:button {key=\"cancel\";label=\"Cancelar\";is_cancel=true;}}}\nXYZ_PROCESS : dialog {label=\"XYZ-Tools - Procesar archivo / Unir XYZ\";:row {:edit_box {key=\"file\";label=\"Archivo\";edit_width=70;edit_limit=1024;}:button {key=\"pick_input\";label=\"Buscar...\";}}:row {:column {:boxed_column {label=\"Lectura\";:popup_list {key=\"sep\";label=\"Separador\";width=34;}:popup_list {key=\"decimal\";label=\"Decimales\";width=34;}:row {:edit_box {key=\"cx\";label=\"X col.\";edit_width=3;edit_limit=1024;}:edit_box {key=\"cy\";label=\"Y col.\";edit_width=3;edit_limit=1024;}:edit_box {key=\"cz\";label=\"Z col.\";edit_width=3;edit_limit=1024;}}:edit_box {key=\"skip\";label=\"Omitir primeras filas\";edit_width=5;edit_limit=1024;}}:boxed_column {label=\"Operacion\";:popup_list {key=\"operation\";label=\"Modo\";width=34;}:edit_box {key=\"amount\";label=\"Offset Z\";edit_width=10;edit_limit=1024;}:edit_box {key=\"ranges\";label=\"Rangos: min max ajuste; ...\";edit_width=38;edit_limit=1024;}:row {:edit_box {key=\"remove_min\";label=\"Eliminar desde Z\";edit_width=8;edit_limit=1024;}:edit_box {key=\"remove_max\";label=\"Hasta Z\";edit_width=8;edit_limit=1024;}}:popup_list {key=\"badrows\";label=\"Filas no numericas\";width=34;}}}:column {:boxed_column {label=\"Union (orden de prioridad)\";" f)
  (write-line ":list_box {key=\"files\";width=60;height=8;}:row {:button {key=\"add_file\";label=\"Agregar archivo\";}:button {key=\"remove_file\";label=\"Quitar seleccionado\";}}:popup_list {key=\"duplicates\";label=\"Duplicados\";width=34;}:edit_box {key=\"tol\";label=\"Tolerancia 3D\";edit_width=10;edit_limit=1024;}:text {label=\"Todas las fuentes deben usar mismo sistema y unidades.\";}}:boxed_column {label=\"Salida\";:edit_box {key=\"suffix\";label=\"Sufijo automatico\";edit_width=12;edit_limit=1024;}:edit_box {key=\"outdec\";label=\"Decimales (-1 = automatico)\";edit_width=5;edit_limit=1024;}:row {:edit_box {key=\"output\";label=\"Destino (vacio = automatico)\";edit_width=35;edit_limit=1024;}:button {key=\"pick_output\";label=\"Elegir...\";}}:toggle {key=\"import_after\";label=\"Importar resultado al dibujo con ajustes actuales\";}}}}:text {key=\"process_status\";width=34;}:row {:button {key=\"preview\";label=\"Vista previa\";}:spacer {width=15;}:button {key=\"accept\";label=\"Ejecutar\";is_default=true;}:button {key=\"cancel\";label=\"Cancelar\";is_cancel=true;}}}\nXYZ_LABELS : dialog {label=\"XYZ-Tools - Etiquetas de elevacion\";:toggle {key=\"labels\";label=\"Anotar Z de cada punto importado\";}:row {:edit_box {key=\"labelheight\";label=\"Altura\";edit_width=8;edit_limit=1024;}:edit_box {key=\"labelwidth\";label=\"Factor de ancho\";edit_width=8;edit_limit=1024;}}:row {:edit_box {key=\"labelsep\";label=\"Separacion en Y\";edit_width=8;edit_limit=1024;}" f)
  (write-line ":edit_box {key=\"labeldec\";label=\"Decimales\";edit_width=4;edit_limit=1024;}}:edit_box {key=\"labelstyle\";label=\"Estilo (si falta se usa Standard)\";edit_width=20;edit_limit=1024;}:toggle {key=\"labelabs\";label=\"Mostrar valor absoluto de Z (solo texto)\";}:toggle {key=\"labelz\";label=\"Texto en elevacion del punto (desactivado = Z 0)\";}:toggle {key=\"labelone\";label=\"Todas las etiquetas en una capa del lote\";}:edit_box {key=\"labellayer\";label=\"Prefijo de capa de etiquetas\";edit_width=25;edit_limit=1024;}:text {label=\"El texto conserva el color de la clase del punto.\";}:row {:button {key=\"accept\";label=\"Guardar\";is_default=true;}:button {key=\"cancel\";label=\"Cancelar\";is_cancel=true;}}}\nXYZ_POINTTOOLS : dialog {label=\"XYZ-Tools - P-Z: Puntos Z\";:popup_list {key=\"pt_operation\";label=\"Operacion\";width=34;}:popup_list {key=\"pt_source\";label=\"Fuente de datos\";width=34;}:edit_box {key=\"pt_offset\";label=\"Desplazamiento Z (OZ)\";edit_width=12;edit_limit=1024;}:row {:edit_box {key=\"pt_file\";label=\"Archivo\";edit_width=50;edit_limit=1024;}:button {key=\"pick_file\";label=\"Buscar...\";}}:popup_list {key=\"pt_format\";label=\"Formato de archivo\";width=34;}:text {label=\"Archivo abre el procesador completo; permite revisar columnas y salida.\";}:text {label=\"IZ y ZM: puntos POINT. OZ: desplazamiento en Z mundial.\";}:row {:button {key=\"accept\";label=\"Continuar\";is_default=true;}:button {key=\"cancel\";" f)
  (write-line "label=\"Cancelar\";is_cancel=true;}}}" f)
  (close f) (setq *xyzt:out* nil))
;;; ============================================================================
;;; Funciones conservadas/ampliadas de XYZ-Tools 2.3: etiquetas, procesar y unir.
;;; Procesar conserva X/Y y campos adicionales; solo transforma la columna Z.
;;; Unir genera XYZ normalizado, sin acumular todos los puntos en una lista.
;;; ============================================================================
(defun xyz:replace-index (items index value / out j item)
  (setq out nil j 0)
  (foreach item items (setq out (cons (if (= j index) value item) out) j (1+ j)))
  (reverse out))
(defun xyz:number-text (number decimals decimal / text)
  (setq text (rtos number 2 (if (= decimals -1) 16 decimals)))
  (if (= decimals -1)
    (progn
      (while (and (> (strlen text) 1) (= (substr text (strlen text) 1) "0")
                  (vl-string-search "." text))
        (setq text (substr text 1 (1- (strlen text)))))
      (if (= (substr text (strlen text) 1) ".") (setq text (substr text 1 (1- (strlen text)))))))
  (if (member text '("-0" "-0.0")) (setq text "0"))
  (if (= decimal ",") (vl-string-translate "." "," text) text))
(defun xyz:join (items sep / text item)
  (setq text nil)
  (foreach item items
    (setq text (if text (strcat text sep item) item)))
  (if text text ""))
(defun xyz:output-row (fields sep / item result)
  (setq result nil)
  (foreach item fields
    (setq result (cons (if (or (vl-string-search sep item) (vl-string-search "\"" item)
                              (and (= sep " ") (vl-string-search (chr 9) item)))
                        (xyzt:csv-quote item) item) result)))
  (xyz:join (reverse result) sep))
(defun xyz:parse-ranges (text / chunks items out vals part a b delta previous entry)
  (setq chunks (xyzt:fields text ";") out nil)
  (foreach part chunks
    (if (/= (xyzt:trim part) "")
      (progn
        (setq items (xyzt:fields part "WS"))
        (if (/= (length items) 3) (xyzt:fail "Cada rango debe tener: Z_min Z_max ajuste. Separe rangos con ;"))
        (setq a (xyzt:setting-number (car items)) b (xyzt:setting-number (cadr items))
              delta (xyzt:setting-number (caddr items)))
        (if (or (null a) (null b) (null delta) (>= a b)) (xyzt:fail "Rango invalido: requiere Z_min < Z_max y ajuste numerico."))
        (setq out (cons (list a b delta) out)))))
  (if (not out) (xyzt:fail "Ingrese al menos un rango."))
  (setq out (vl-sort out '(lambda (a b) (< (car a) (car b)))) previous nil)
  (foreach entry out
    (if (and previous (< (car entry) (cadr previous))) (xyzt:fail "Los rangos se superponen. Corrija los limites."))
    (setq previous entry)) out)
(defun xyz:transform (z mode offset ranges lo hi / entry value matched lastentry)
  (cond
    ((= mode 0) (- z))
    ((= mode 1) (+ z offset))
    ((= mode 2)
      (setq value z matched nil lastentry (last ranges))
      (foreach entry ranges
        (if (and (not matched) (>= z (car entry))
                 (or (< z (cadr entry)) (and (equal entry lastentry) (<= z (cadr entry)))))
          (setq value (+ z (caddr entry)) matched T))) value)
    ((= mode 3) (if (and (>= z lo) (<= z hi)) nil z))
    (T z)))
(defun xyz:identity-config (cfg)
  (setq cfg (xyzt:put 'xyfactor 1.0 cfg) cfg (xyzt:put 'zfactor 1.0 cfg) cfg (xyzt:put 'offset 0.0 cfg)) cfg)
(defun xyz:process-defaults (file / cfg pair)
  (setq cfg (xyzt:defaults) cfg (xyzt:put "file" file cfg))
  (foreach pair '(("operation" . "0") ("amount" . "0") ("ranges" . "-20 -10 0.1; -10 0 0.2")
      ("remove_min" . "-9999") ("remove_max" . "-9998") ("outdec" . "-1")
      ("suffix" . "_MOD") ("output" . "") ("badrows" . "0") ("import_after" . "0"))
    (setq cfg (xyzt:put (car pair) (cdr pair) cfg))) cfg)
(setq xyz:process-keys '("file" "sep" "decimal" "cx" "cy" "cz" "skip" "operation" "amount"
  "ranges" "remove_min" "remove_max" "outdec" "suffix" "output" "badrows" "import_after" "duplicates" "tol"))
(defun xyz:process-save (/ key)
  (foreach key xyz:process-keys (setq *xyz:process-ui* (xyzt:put key (get_tile key) *xyz:process-ui*))))
(defun xyz:process-exit (code) (xyz:process-save) (done_dialog code))
(defun xyz:process-dialog (/ key path)
  (if (not (new_dialog "XYZ_PROCESS" *xyzt:dclid*)) (xyzt:fail "No se pudo abrir Procesar/Unir."))
  (xyzt:fill-popup "sep" '("Automatico" "Espacios/TAB" "TAB" "Punto y coma" "Coma"))
  (xyzt:fill-popup "decimal" '("Punto decimal" "Coma decimal"))
  (xyzt:fill-popup "operation" '("Invertir Z" "Offset constante Z" "Ajustar Z por rangos" "Eliminar rango Z" "Unir archivos XYZ" "Analizar Z minima / maxima"))
  (xyzt:fill-popup "badrows" '("Conservar filas no numericas (procesar)" "Omitir filas no numericas (procesar)"))
  (xyzt:fill-popup "duplicates" '("Conservar duplicados (union)" "Eliminar XYZ exactos (union)" "Tolerancia distancia 3D (union)"))
  (foreach key xyz:process-keys (set_tile key (xyzt:get key *xyz:process-ui*)))
  (start_list "files") (foreach path *xyz:files* (add_list path)) (end_list)
  (set_tile "process_status" (strcat "Archivos de union: " (itoa (length *xyz:files*)) ". Rangos: [min,max); ultimo incluye max."))
  (action_tile "pick_input" "(xyz:process-exit 2)")
  (action_tile "add_file" "(xyz:process-exit 3)")
  (action_tile "remove_file" "(setq *xyz:remove-index* (atoi (get_tile \"files\")))(xyz:process-exit 4)")
  (action_tile "pick_output" "(xyz:process-exit 5)")
  (action_tile "preview" "(xyz:process-exit 6)")
  (action_tile "accept" "(xyz:process-exit 1)")
  (action_tile "cancel" "(xyz:process-exit 0)")
  (start_dialog))
(defun xyz:validate-process (cfg files / key value mode file)
  (setq mode (atoi (xyzt:get "operation" cfg)))
  (if (= mode 4)
    (progn
      (if (< (length files) 2) (xyzt:fail "Agregue al menos dos archivos a la union."))
      (foreach file files (if (not (findfile file)) (xyzt:fail (strcat "No existe: " file))))
      (setq cfg (xyzt:put "file" (car files) cfg))))
  (setq cfg (xyzt:validate cfg) cfg (xyz:identity-config cfg))
  (foreach key '("amount" "remove_min" "remove_max" "outdec")
    (setq value (xyzt:setting-number (xyzt:get key cfg)))
    (if (or (null value) (> (abs value) 1e10)) (xyzt:fail (strcat "Valor invalido: " key)))
    (setq cfg (xyzt:put (read (strcat "p-" key)) value cfg)))
  (setq value (xyzt:get 'p-outdec cfg))
  (if (or (/= value (fix value)) (< value -1) (> value 16)) (xyzt:fail "Decimales de salida: -1 automatico o un entero de 0 a 16."))
  (if (and (= mode 3) (> (xyzt:get 'p-remove_min cfg) (xyzt:get 'p-remove_max cfg)))
    (xyzt:fail "Limites del rango a eliminar invertidos."))
  (if (= mode 2) (setq cfg (xyzt:put 'p-ranges (xyz:parse-ranges (xyzt:get "ranges" cfg)) cfg)))
  (if (= (xyzt:trim (xyzt:get "suffix" cfg)) "") (setq cfg (xyzt:put "suffix" "_MOD" cfg)))
  cfg)
(defun xyz:same-path (a b)
  (equal (strcase (vl-string-translate "/" "\\" a)) (strcase (vl-string-translate "/" "\\" b))))
(defun xyz:unique-path (path / folder base ext idx result)
  (setq folder (vl-filename-directory path) base (vl-filename-base path) ext (vl-filename-extension path)
        idx 1 result path)
  (if (not ext) (setq ext ".xyz" result (strcat path ext)))
  (while (findfile result)
    (setq result (strcat folder "\\" base "_" (itoa idx) ext) idx (1+ idx))) result)
(defun xyz:process-output (cfg files / path file base)
  (setq path (xyzt:get "output" cfg))
  (if (= path "")
    (setq path (strcat (vl-filename-directory (xyzt:get "file" cfg)) "\\"
      (vl-filename-base (xyzt:get "file" cfg)) (if (= (xyzt:get "operation" cfg) "4") "_UNIDO" (xyzt:get "suffix" cfg)) ".xyz")))
  (foreach file files
    (if (xyz:same-path path file) (xyzt:fail "La salida coincide con un original. Elija otro nombre.")))
  (if (not (vl-file-directory-p (vl-filename-directory path))) (xyzt:fail "No existe la carpeta de salida."))
  (xyz:unique-path path))
(defun xyz:control (kind file line reason value)
  (write-line (strcat kind ";" (xyzt:csv-quote file) ";" (itoa line) ";" reason ";" (xyzt:csv-quote value)) *xyzt:log*))
(defun xyz:signature (file) (list (vl-file-size file) (vl-file-systime file)))
(defun xyz:process-engine (cfg files output / temp control reporttemp f file per sep s ln p fields z value
                              mode decimals delim total written invalid removed duplicates skipped dup source-signature count result)
  (setq mode (atoi (xyzt:get "operation" cfg)) decimals (fix (xyzt:get 'p-outdec cfg))
        total 0 written 0 invalid 0 removed 0 duplicates 0 skipped 0
        temp (vl-filename-mktemp "xyzt_data_" (vl-filename-directory output) ".tmp")
        control (xyz:unique-path (strcat (vl-filename-directory output) "\\" (vl-filename-base output) "_CONTROL.csv"))
        reporttemp (vl-filename-mktemp "xyzt_control_" (vl-filename-directory output) ".tmp"))
  (setq *xyz:workfiles* (list temp reporttemp))
  (setq *xyzt:out* (open temp "w") *xyzt:log* (open reporttemp "w"))
  (if (or (not *xyzt:out*) (not *xyzt:log*)) (xyzt:fail "No se pudo crear salida temporal/control. Revise permisos de carpeta."))
  (write-line "Seccion;Archivo;Linea;Motivo;Valor" *xyzt:log*)
  (xyz:control "METADATO" "" 0 "VERSION" *xyzt:version*)
  (foreach result cfg
    (if (eq (type (car result)) 'STR) (xyz:control "CONFIG" "" 0 (car result) (cdr result))))
  (setq dup (if (and (= mode 4) (/= (xyzt:get "duplicates" cfg) "0")) (xyzt:new-dict) nil))
  (foreach file files
    (setq per (xyzt:put "file" file cfg) source-signature (xyz:signature file)
          sep (xyzt:detect per) f (xyzt:open-input file) ln 0 count 0)
    (setq delim (cond ((= sep "WS") " ") (T sep)))
    (while (setq s (xyzt:read-line f))
      (setq ln (1+ ln) total (1+ total))
      (cond
        ((or (<= ln (atoi (xyzt:get "skip" cfg))) (xyzt:comment s) (xyzt:header s per sep))
          (setq skipped (1+ skipped))
          (if (/= mode 4) (write-line s *xyzt:out*)))
        ((not (setq p (xyzt:line s per sep)))
          (setq invalid (1+ invalid)) (xyz:control "INCIDENCIA" file ln "XYZ_INVALIDO" s)
          (if (and (/= mode 4) (= (xyzt:get "badrows" cfg) "0")) (write-line s *xyzt:out*)))
        ((and dup (xyzt:duplicate dup p per))
          (setq duplicates (1+ duplicates)) (xyz:control "INCIDENCIA" file ln "DUPLICADO" s))
        (T
          (setq z (caddr p) value (xyz:transform z mode (xyzt:get 'p-amount cfg) (xyzt:get 'p-ranges cfg)
                                    (xyzt:get 'p-remove_min cfg) (xyzt:get 'p-remove_max cfg)))
          (if (null value)
            (progn (setq removed (1+ removed)) (xyz:control "INCIDENCIA" file ln "ELIMINADO_RANGO_Z" s))
            (progn
              (if (= mode 4)
                (write-line (xyz:join (mapcar '(lambda (v) (xyz:number-text v decimals ".")) p) " ") *xyzt:out*)
                (progn
                  (setq fields (xyzt:fields s sep)
                        fields (xyz:replace-index fields (1- (atoi (xyzt:get "cz" cfg)))
                          (xyz:number-text value decimals (xyzt:decimal per))))
                  (write-line (xyz:output-row fields delim) *xyzt:out*)))
              (setq written (1+ written) count (1+ count))))))
      (if (= 0 (rem total 10000)) (princ (strcat "\rXYZ-Tools: " (itoa total) " lineas, " (itoa written) " puntos escritos..."))))
    (xyzt:close-input)
    (if (not (equal source-signature (xyz:signature file))) (xyzt:fail "Cambio un archivo fuente durante el proceso. Se cancelo la salida."))
    (xyz:control "FUENTE" file ln "PUNTOS_ESCRITOS" (itoa count)))
  (if (= written 0) (xyzt:fail "La operacion no produjo puntos. No se publico un archivo vacio."))
  (foreach result (list (cons "LINEAS" total) (cons "PUNTOS" written) (cons "INVALIDAS" invalid)
                        (cons "ELIMINADAS" removed) (cons "DUPLICADOS" duplicates) (cons "OMITIDAS" skipped))
    (xyz:control "RESUMEN" "" 0 (car result) (itoa (cdr result))))
  (close *xyzt:out*) (setq *xyzt:out* nil) (close *xyzt:log*) (setq *xyzt:log* nil)
  ;; La publicacion solo ocurre tras cerrar y validar todos los archivos.
  (if (not (vl-file-rename reporttemp control)) (xyzt:fail "No se pudo publicar el control CSV."))
  (setq *xyz:workfiles* (cons control *xyz:workfiles*))
  (if (not (vl-file-rename temp output)) (xyzt:fail "No se pudo publicar XYZ. No se sobrescribio ningun original."))
  (setq *xyz:workfiles* nil)
  (princ (strcat "\nXYZ-Tools: " (itoa written) " puntos.\nArchivo: " output "\nControl: " control))
  (list (cons 'output output) (cons 'count written) (cons 'control control)))
(defun xyz:preview-process (cfg / sep f s ln shown p value fields text)
  (setq sep (xyzt:detect cfg) f (xyzt:open-input (xyzt:get "file" cfg)) ln 0 shown 0 text "Vista previa (no escribe archivos):\n")
  (while (and (< shown 6) (setq s (xyzt:read-line f)))
    (setq ln (1+ ln))
    (if (and (> ln (atoi (xyzt:get "skip" cfg))) (setq p (xyzt:line s cfg sep)))
      (progn
        (setq value (xyz:transform (caddr p) (atoi (xyzt:get "operation" cfg)) (xyzt:get 'p-amount cfg)
          (xyzt:get 'p-ranges cfg) (xyzt:get 'p-remove_min cfg) (xyzt:get 'p-remove_max cfg)))
        (setq text (strcat text "\nLinea " (itoa ln) " | Z " (xyzt:nstr (caddr p)) " -> "
          (if value (xyz:number-text value (fix (xyzt:get 'p-outdec cfg)) (xyzt:decimal cfg)) "ELIMINAR")))
        (setq shown (1+ shown)))))
  (xyzt:close-input) (alert text))
(defun xyz:process-flow (merge / cfg code result path validated output item n rest)
  (if (not *xyz:last-process*) (setq *xyz:last-process* (xyz:process-defaults (xyzt:get "file" *xyzt:ui*))))
  (setq *xyz:process-ui* *xyz:last-process* *xyz:files* nil code -1 result nil)
  (if (/= (xyzt:get "file" *xyzt:ui*) "")
    (setq *xyz:process-ui* (xyzt:put "file" (xyzt:get "file" *xyzt:ui*) *xyz:process-ui*)))
  (if merge
    (progn
      (setq *xyz:process-ui* (xyzt:put "operation" "4" *xyz:process-ui*))
      (if (findfile (xyzt:get "file" *xyz:process-ui*)) (setq *xyz:files* (list (xyzt:get "file" *xyz:process-ui*))))))
  (while (and (/= code 0) (/= code 1))
    (setq code (xyz:process-dialog))
    (cond
      ((= code 2)
        (setq path (getfiled "Archivo a procesar" (xyzt:get "file" *xyz:process-ui*) "xyz;txt;csv;asc" 0))
        (if path (setq *xyz:process-ui* (xyzt:put "file" path *xyz:process-ui*))))
      ((= code 3)
        (setq path (getfiled "Agregar archivo a la union" (xyzt:get "file" *xyz:process-ui*) "xyz;txt;csv;asc" 0))
        (if path
          (if (vl-some '(lambda (old) (xyz:same-path old path)) *xyz:files*)
            (alert "Ese archivo ya esta en la lista.")
            (setq *xyz:files* (append *xyz:files* (list path))))))
      ((= code 4)
        (setq rest nil n 0)
        (foreach item *xyz:files* (if (/= n *xyz:remove-index*) (setq rest (cons item rest))) (setq n (1+ n)))
        (setq *xyz:files* (reverse rest)))
      ((= code 5)
        (setq path (getfiled "Destino XYZ (si existe se usa un nombre nuevo)" (xyzt:get "output" *xyz:process-ui*) "xyz" 33))
        (if path (setq *xyz:process-ui* (xyzt:put "output" path *xyz:process-ui*))))
      ((member code '(1 6))
        (setq validated (xyzt:try 'xyz:validate-process (list *xyz:process-ui* *xyz:files*)))
        (if (vl-catch-all-error-p validated) (progn (alert (xyzt:errmsg validated)) (setq code -1))
          (progn
            (setq cfg validated)
            (if (= code 6)
              (progn
                (setq validated (xyzt:try 'xyz:preview-process (list cfg)))
                (if (vl-catch-all-error-p validated) (progn (xyzt:close-input) (alert (xyzt:errmsg validated)))))
              (if (/= (xyzt:get "operation" cfg) "5")
                (setq output (xyz:process-output cfg (if (= (xyzt:get "operation" cfg) "4") *xyz:files* (list (xyzt:get "file" cfg))))))))))))
  (setq *xyz:last-process* *xyz:process-ui*)
  (if (= code 1)
    (if (= (xyzt:get "operation" cfg) "5")
      (progn (xyz:file-z-stats cfg) (setq result nil))
      (progn
      (setq result (xyz:process-engine cfg (if (= (xyzt:get "operation" cfg) "4") *xyz:files* (list (xyzt:get "file" cfg))) output))
      (alert (strcat "Archivo generado\n" output "\nPuntos: " (itoa (xyzt:get 'count result)) "\nLos originales se conservaron."))
      (if (= (xyzt:get "import_after" cfg) "1")
        (progn
          (setq *xyzt:ui* (xyzt:put "file" output *xyzt:ui*) *xyzt:ui* (xyzt:put "skip" "0" *xyzt:ui*)
                *xyzt:ui* (xyzt:put "zmode" "0" *xyzt:ui*) *xyzt:ui* (xyzt:put "dz" "0" *xyzt:ui*))
          (foreach item '("sep" "decimal" "cx" "cy" "cz")
            (setq *xyzt:ui* (xyzt:put item (if (= (xyzt:get "operation" cfg) "4")
              (cdr (assoc item '(("sep" . "1") ("decimal" . "0") ("cx" . "1") ("cy" . "2") ("cz" . "3"))))
              (xyzt:get item cfg)) *xyzt:ui*)))
          ;; Procesar conserva encabezados y columnas; repetir skip original.
          (if (/= (xyzt:get "operation" cfg) "4") (setq *xyzt:ui* (xyzt:put "skip" (xyzt:get "skip" cfg) *xyzt:ui*)))
          (setq result T))
        (setq result nil))))) result)

;;; Etiquetas de Z: estilos, ancho, separacion, decimales, absoluto y capa unica.
(setq xyz:label-keys '("labels" "labelheight" "labelwidth" "labelsep" "labeldec" "labelabs" "labelone" "labellayer" "labelstyle" "labelz"))
(defun xyz:labels-dialog (/ code key)
  (if (not (new_dialog "XYZ_LABELS" *xyzt:dclid*)) (xyzt:fail "No se pudo abrir Etiquetas."))
  (foreach key xyz:label-keys (set_tile key (xyzt:get key *xyzt:ui*)))
  (action_tile "accept" "(done_dialog 1)") (action_tile "cancel" "(done_dialog 0)")
  ;; Los valores se capturan antes de cerrar el dialogo.
  (action_tile "accept" "(foreach key xyz:label-keys (setq *xyzt:ui* (xyzt:put key (get_tile key) *xyzt:ui*)))(done_dialog 1)")
  (start_dialog))
(defun xyz:validate-labels (cfg / key value style name)
  (if (= (xyzt:get "labels" cfg) "1")
    (progn
      (foreach key '("labelheight" "labelwidth" "labelsep" "labeldec")
        (setq value (xyzt:setting-number (xyzt:get key cfg)))
        (if (or (null value) (> (abs value) 1e6)) (xyzt:fail (strcat "Etiqueta: numero invalido en " key)))
        (setq cfg (xyzt:put (read (strcat "v-" key)) value cfg)))
      (if (or (<= (xyzt:get 'v-labelheight cfg) 0) (<= (xyzt:get 'v-labelwidth cfg) 0) (< (xyzt:get 'v-labelsep cfg) 0))
        (xyzt:fail "Altura/ancho deben ser positivos y separacion no negativa."))
      (setq value (xyzt:get 'v-labeldec cfg))
      (if (or (/= value (fix value)) (< value 0) (> value 16)) (xyzt:fail "Decimales de etiqueta: entero entre 0 y 16."))
      (setq style (xyzt:trim (xyzt:get "labelstyle" cfg)))
      (if (or (= style "") (not (tblsearch "STYLE" style)))
        (progn (princ "\nEstilo de etiqueta no encontrado; se utilizara Standard.") (setq style "Standard")))
      (setq cfg (xyzt:put "labelstyle" style cfg) name (xyzt:trim (xyzt:get "labellayer" cfg)))
      (if (and (= (xyzt:get "labelone" cfg) "1") (or (= name "") (> (strlen name) 40) (not (snvalid name))))
        (xyzt:fail "Nombre de capa de etiquetas invalido (maximo 40 caracteres).")))) cfg)
(defun xyz:label (p ln lot info cfg / target pos z en)
  (setq target (if (= (xyzt:get "labelone" cfg) "1") *xyz:label-layer* (car info))
        z (if (= (xyzt:get "labelz" cfg) "1") (caddr p) 0.0)
        pos (list (car p) (- (cadr p) (xyzt:get 'v-labelsep cfg)) z))
  (xyzt:make (list '(0 . "TEXT") '(100 . "AcDbEntity") (cons 8 target)
    (cons 420 (xyzt:tc (nth 3 info))) '(100 . "AcDbText")
    (cons 10 pos) (cons 11 pos) '(72 . 1) '(73 . 0)
    (cons 40 (xyzt:get 'v-labelheight cfg)) (cons 41 (xyzt:get 'v-labelwidth cfg))
    (cons 7 (xyzt:get "labelstyle" cfg))
    (cons 1 (rtos (if (= (xyzt:get "labelabs" cfg) "1") (abs (caddr p)) (caddr p)) 2 (fix (xyzt:get 'v-labeldec cfg))))
    (xyzt:tag lot ln))))
(defun c:IXYZ () (setq *xyz:entry* nil) (c:XYZ))
(defun c:PZ () (setq *xyz:entry* "process") (c:XYZ))
(defun c:XYZUNIR () (setq *xyz:entry* "merge") (c:XYZ))

;;; ============================================================================
;;; Integracion de Procesa_Puntos (P-Z): operaciones en dibujo y consulta de Z.
;;; IZ y ZM: POINT; OZ: traslacion WCS nativa de todos los tipos admitidos.
;;; No se cambian escalas, rotaciones, capas ni propiedades por mover entidades.
;;; ============================================================================
(defun xyz:screen-point (point mode distance)
  (list (car point) (cadr point) (if (= mode "IZ") (- (caddr point)) (+ (caddr point) distance))))
(defun xyz:locked (en / ed layer flags)
  (setq ed (entget en) layer (tblsearch "LAYER" (cdr (assoc 8 ed)))
        flags (cdr (assoc 70 layer)))
  (and flags (/= 0 (logand 4 flags))))
(defun xyz:restore-changes (changes / change res failed)
  (setq failed 0)
  (foreach change changes
    (setq res
      (if (= (car change) "MOVE")
        (vl-catch-all-apply 'vla-Move
          (list (vlax-ename->vla-object (cadr change)) (vlax-3d-point '(0.0 0.0 0.0))
            (vlax-3d-point (list 0.0 0.0 (- (caddr change))))))
        (vl-catch-all-apply 'entmod (list (caddr change)))))
    (if (or (vl-catch-all-error-p res) (and (= (car change) "ENTMOD") (not res)))
      (setq failed (1+ failed)))) failed)
(defun xyz:mark-edited-lots (lots mode changes / root lot rec ed updated)
  (setq root (dictsearch (namedobjdict) "IXYZ7_LOTES"))
  (if root
    (foreach lot lots
      (if (setq rec (dictsearch (cdr (assoc -1 root)) lot))
        (progn
          (setq ed (entget (cdr (assoc -1 rec))))
          (setq updated (append ed (list (cons 1 (strcat "EDICION_EN_DIBUJO=" mode "; revisar etiquetas, clases y leyenda")))))
          ;; Se devuelve historial de restauracion, incluida la metainformacion.
          (if (entmod updated)
            (setq changes (cons (list "ENTMOD" (cdr (assoc -1 rec)) ed) changes) *xyz:screen-log* changes)
            (princ (strcat "\nNo se pudo marcar el historial del lote " lot))))))) changes)
(defun xyz:print-z-stats (stat title / n minz maxz text)
  (setq n (car (car stat)))
  (if (= n 0) (princ "\nNo hay puntos validos para analizar.")
    (progn
      (setq minz (cadr stat) maxz (caddr stat))
      (setq text (strcat title "\nPuntos: " (itoa n)
        "\nZ minima: " (xyzt:nstr minz) "\nZ maxima: " (xyzt:nstr maxz)
        "\nDiferencia: " (xyzt:nstr (- maxz minz))
        "\nPunto medio del rango Z: " (xyzt:nstr (/ (+ minz maxz) 2.0))
        "\nPromedio de Z: " (xyzt:nstr (cadr (car stat)))
        "\nDesviacion estandar muestral: " (xyzt:nstr (xyzt:std stat))))
      (princ (strcat "\n" text)) (alert text)))
  stat)
(defun xyz:screen-operation (mode distance / *error* doc mark changes selection i en ed point changed
                              obj processed locked omitted stat lot lots rollback-failed saved-failure)
  (setq doc (vla-get-ActiveDocument (vlax-get-acad-object)) mark nil changes nil
        processed 0 locked 0 omitted 0 stat (xyzt:empty-stat) lots nil *xyzt:failure* nil *xyz:screen-log* nil)
  (defun *error* (msg)
    (setq msg (if *xyzt:failure* *xyzt:failure* msg) *xyzt:failure* nil)
    (setq rollback-failed (xyz:restore-changes *xyz:screen-log*))
    (if mark (vl-catch-all-apply 'vla-EndUndoMark (list doc)))
    ;; Cuando se invoca desde el panel XYZ tambien se libera su interfaz temporal.
    (if (and *xyzt:dclid* (numberp savedcm) (numberp saveddz) (numberp savedpd))
      (progn (xyzt:cleanup) (setvar "CMDECHO" savedcm) (setvar "DIMZIN" saveddz) (setvar "PDSIZE" savedpd)))
    (princ (strcat "\n" mode " detenido: " (if msg msg "sin mensaje")))
    (if (> rollback-failed 0)
      (princ (strcat "\nNo se pudieron restaurar " (itoa rollback-failed) " cambios; revise el dibujo y use U."))
      (if changes (princ "\nSe restauraron los objetos modificados durante esta operacion.")))
    (setq *xyz:screen-log* nil)
    (princ))
  (if (and (= mode "OZ") (not (numberp distance))) (xyzt:fail "El desplazamiento Z debe ser numerico."))
  (if (and (= mode "OZ") (= distance 0.0)) (princ "\nDesplazamiento cero: sin cambios.")
    (progn
      (princ (if (= mode "OZ") "\nSeleccione objetos a desplazar en Z mundial: " "\nSeleccione puntos POINT: "))
      (setq selection (ssget
        (if (= mode "OZ")
          '((0 . "POINT,3DFACE,*POLYLINE,LINE,SPLINE,INSERT,REGION,SOLID,3DSOLID,MESH,TEXT,MTEXT,CIRCLE,ARC,ELLIPSE"))
          '((0 . "POINT")))))
      (if selection
        (progn
          (if (/= mode "ZM")
            (progn
              (if (= 0 (logand 1 (getvar "UNDOCTL"))) (xyzt:fail "Active DESHACER antes de modificar objetos."))
              (vla-StartUndoMark doc) (setq mark T)))
          (setq i 0)
          (repeat (sslength selection)
            (setq en (ssname selection (float i)) ed (entget en))
            (cond
              ((= mode "ZM")
                (setq point (cdr (assoc 10 ed)))
                (if (and point (= (length point) 3))
                  (setq stat (xyzt:stat-add stat point) processed (1+ processed))
                  (setq omitted (1+ omitted))))
              ((xyz:locked en) (setq locked (1+ locked)))
              ((= mode "IZ")
                (setq point (cdr (assoc 10 ed)))
                (if (and point (= (length point) 3))
                  (progn
                    (setq changed (subst (cons 10 (xyz:screen-point point "IZ" 0.0)) (assoc 10 ed) ed))
                    (if (not (entmod changed)) (xyzt:fail "No se pudo cambiar un punto. Se restaura la seleccion."))
                    (setq changes (cons (list "ENTMOD" en ed) changes) *xyz:screen-log* changes processed (1+ processed)))
                  (setq omitted (1+ omitted))))
              (T
                ;; vla-Move expresa el vector en WCS y respeta OCS de bloques/polilineas.
                (setq obj (vlax-ename->vla-object en))
                (vla-Move obj (vlax-3d-point '(0.0 0.0 0.0)) (vlax-3d-point (list 0.0 0.0 distance)))
                (setq changes (cons (list "MOVE" en distance) changes) *xyz:screen-log* changes processed (1+ processed))))
            (if (and (/= mode "ZM") (not (xyz:locked en)) (setq lot (xyzt:lot-of en)) (not (member lot lots)))
              (setq lots (cons lot lots)))
            (setq i (1+ i)))
          (if (= mode "ZM") (xyz:print-z-stats stat "Z Min / Max - puntos del dibujo")
            (progn
              (setq changes (xyz:mark-edited-lots lots mode changes))
              (vla-EndUndoMark doc) (setq mark nil changes nil *xyz:screen-log* nil)
              (vl-catch-all-apply 'vla-Regen (list doc 1))
              (princ (strcat "\n" mode ": " (itoa processed) " objetos modificados; " (itoa locked)
                " en capas bloqueadas; " (itoa omitted) " omitidos."))
              (if lots
                (princ "\nLotes marcados como editados: sus etiquetas, clases y leyendas requieren revision.")))))
        (princ "\nNo se seleccionaron objetos compatibles."))))
  (princ))
(defun xyz:file-z-stats (cfg / stats)
  (setq stats (xyzt:analyze (xyz:identity-config cfg) nil (xyzt:detect cfg)))
  (xyz:print-z-stats (xyzt:get 'raw stats) (strcat "Z Min / Max - archivo\n" (xyzt:get "file" cfg)))
  (princ (strcat "\nFilas no validas: " (itoa (xyzt:get 'invalid stats))
                 " | Encabezados/comentarios/omitidas: " (itoa (xyzt:get 'skip stats))))
  stats)

;;; Panel compatible con P-Z original: Fuente Pantalla/Archivo y Operacion.
(setq xyz:point-keys '("pt_operation" "pt_source" "pt_offset" "pt_file" "pt_format"))
(defun xyz:point-save (/ key)
  (foreach key xyz:point-keys (setq *xyz:point-ui* (xyzt:put key (get_tile key) *xyz:point-ui*))))
(defun xyz:point-exit (code) (xyz:point-save) (done_dialog code))
(defun xyz:point-dialog (/ key)
  (if (not (new_dialog "XYZ_POINTTOOLS" *xyzt:dclid*)) (xyzt:fail "No se pudo abrir el panel P-Z."))
  (xyzt:fill-popup "pt_operation" '("Invertir Z (IZ)" "Offset Z (OZ)" "Z minima / maxima (ZM)" "Unir archivos XYZ"))
  (xyzt:fill-popup "pt_source" '("En pantalla" "Archivo XYZ / TXT / CSV"))
  (xyzt:fill-popup "pt_format" '("Columnas X Y Z" "Columnas N / ID, X, Y, Z"))
  (foreach key xyz:point-keys (set_tile key (xyzt:get key *xyz:point-ui*)))
  (action_tile "pick_file" "(xyz:point-exit 2)")
  (action_tile "accept" "(xyz:point-exit 1)")
  (action_tile "cancel" "(xyz:point-exit 0)")
  (action_tile "pt_source" "(xyz:point-ui-state)")
  (action_tile "pt_operation" "(xyz:point-ui-state)")
  (xyz:point-ui-state)
  (start_dialog))
(defun xyz:pointtools-flow (/ code path mode source distance result cfg item)
  (if (not *xyz:point-ui*)
    (setq *xyz:point-ui* (list '("pt_operation" . "0") '("pt_source" . "0") '("pt_offset" . "0")
      (cons "pt_file" (xyzt:get "file" *xyzt:ui*)) '("pt_format" . "0"))))
  (setq code -1 result nil)
  (while (and (/= code 0) (/= code 1))
    (setq code (xyz:point-dialog))
    (if (= code 2)
      (progn
        (setq path (getfiled "Archivo de puntos" (xyzt:get "pt_file" *xyz:point-ui*) "xyz;txt;csv;asc" 0))
        (if path (setq *xyz:point-ui* (xyzt:put "pt_file" path *xyz:point-ui*))))))
  (if (= code 1)
    (progn
      (setq mode (atoi (xyzt:get "pt_operation" *xyz:point-ui*))
            source (xyzt:get "pt_source" *xyz:point-ui*)
            distance (xyzt:setting-number (xyzt:get "pt_offset" *xyz:point-ui*)))
      (if (and (= mode 1) (null distance)) (xyzt:fail "Ingrese un offset Z numerico."))
      (cond
        ((= mode 3)
          (if (= source "0") (xyz:export-screen)
            (setq result (xyz:process-flow T))))
        ((= source "0") (xyz:screen-operation (nth mode '("IZ" "OZ" "ZM")) distance))
        (T
          (setq path (xyzt:get "pt_file" *xyz:point-ui*))
          (if (= path "") (xyzt:fail "Seleccione un archivo de puntos."))
          (setq *xyzt:ui* (xyzt:put "file" path *xyzt:ui*))
          (if (not *xyz:last-process*) (setq *xyz:last-process* (xyz:process-defaults path)))
          (setq *xyz:last-process* (xyzt:put "file" path *xyz:last-process*)
                *xyz:last-process* (xyzt:put "operation" (nth mode '("0" "1" "5")) *xyz:last-process*)
                *xyz:last-process* (xyzt:put "amount" (xyzt:get "pt_offset" *xyz:point-ui*) *xyz:last-process*)
                *xyz:last-process* (xyzt:put "import_after" (if (= mode 2) "0" "1") *xyz:last-process*))
          (setq *xyz:last-process* (xyzt:put "cx" (if (= (xyzt:get "pt_format" *xyz:point-ui*) "1") "2" "1") *xyz:last-process*)
                *xyz:last-process* (xyzt:put "cy" (if (= (xyzt:get "pt_format" *xyz:point-ui*) "1") "3" "2") *xyz:last-process*)
                *xyz:last-process* (xyzt:put "cz" (if (= (xyzt:get "pt_format" *xyz:point-ui*) "1") "4" "3") *xyz:last-process*))
          (setq result (xyz:process-flow nil)))))) result)
(defun c:P-Z () (setq *xyz:entry* "pointtools") (c:XYZ))
(defun c:IZ () (xyz:screen-operation "IZ" 0.0))
(defun c:OZ (/ distance)
  (setq distance (getreal "\nDesplazamiento en Z mundial, positivo o negativo <0>: "))
  (if (null distance) (setq distance 0.0))
  (xyz:screen-operation "OZ" distance))
(defun c:ZM () (xyz:screen-operation "ZM" 0.0))
(defun c:XYZU () (c:XYZUNIR))

;;; Exportacion de POINT seleccionados a archivo XYZ, sin alterar el dibujo.
(defun xyz:export-screen (/ selection path output temp report reporttemp i en ed point count stat source)
  (princ "\nSeleccione puntos POINT a exportar (ventana o seleccion directa): ")
  (setq selection (ssget '((0 . "POINT"))))
  (if selection
    (progn
      (setq path (getfiled "Exportar puntos seleccionados a XYZ" (strcat (getvar "DWGPREFIX") "PUNTOS_EXPORTADOS.xyz") "xyz" 33))
      (if path
        (progn
          (setq output (xyz:unique-path path)
                temp (vl-filename-mktemp "xyzt_export_" (vl-filename-directory output) ".tmp")
                report (xyz:unique-path (strcat (vl-filename-directory output) "\\" (vl-filename-base output) "_CONTROL.csv"))
                reporttemp (vl-filename-mktemp "xyzt_control_" (vl-filename-directory output) ".tmp")
                *xyz:workfiles* (list temp reporttemp)
                *xyzt:out* (open temp "w") *xyzt:log* (open reporttemp "w")
                count 0 i 0 stat (xyzt:empty-stat)
                source (strcat (getvar "DWGPREFIX") (getvar "DWGNAME")))
          (if (or (not *xyzt:out*) (not *xyzt:log*)) (xyzt:fail "No se puede escribir en la carpeta de exportacion."))
          (write-line "Seccion;Archivo;Linea;Motivo;Valor" *xyzt:log*)
          (xyz:control "METADATO" source 0 "OPERACION" "EXPORTAR POINT EN WCS; SIN MODIFICAR EL DIBUJO")
          (repeat (sslength selection)
            (setq en (ssname selection (float i)) ed (entget en) point (cdr (assoc 10 ed)))
            (if (and (= (cdr (assoc 0 ed)) "POINT") (= (length point) 3)
                     (numberp (car point)) (numberp (cadr point)) (numberp (caddr point)))
              (progn
                (write-line (xyz:join (mapcar '(lambda (v) (xyz:number-text v -1 ".")) point) " ") *xyzt:out*)
                (setq count (1+ count) stat (xyzt:stat-add stat point))))
            (setq i (1+ i))
            (if (= 0 (rem i 10000)) (princ (strcat "\rExportados: " (itoa count)))))
          (if (= count 0) (xyzt:fail "No se encontraron puntos validos para exportar."))
          (xyz:control "RESUMEN" source 0 "PUNTOS_EXPORTADOS" (itoa count))
          (xyz:control "RESUMEN" source 0 "XYZ_MIN" (xyzt:serialize (nth 3 stat)))
          (xyz:control "RESUMEN" source 0 "XYZ_MAX" (xyzt:serialize (nth 4 stat)))
          (close *xyzt:out*) (setq *xyzt:out* nil) (close *xyzt:log*) (setq *xyzt:log* nil)
          (if (not (vl-file-rename reporttemp report)) (xyzt:fail "No se pudo publicar el control de exportacion."))
          (setq *xyz:workfiles* (cons report *xyz:workfiles*))
          (if (not (vl-file-rename temp output)) (xyzt:fail "No se pudo publicar XYZ. No se sobrescribieron archivos."))
          (setq *xyz:workfiles* nil)
          (alert (strcat "Exportacion terminada\nPuntos: " (itoa count) "\n" output "\nEl dibujo se conservo."))))))
  (princ))
(defun xyz:point-ui-state (/ source mode current)
  (setq source (get_tile "pt_source") mode (get_tile "pt_operation") current mode)
  (xyzt:fill-popup "pt_operation"
    (if (= source "0")
      '("Invertir Z (IZ)" "Offset Z (OZ)" "Z minima / maxima (ZM)" "Exportar puntos del dibujo")
      '("Invertir Z (IZ)" "Offset Z (OZ)" "Z minima / maxima (ZM)" "Unir archivos XYZ")))
  (set_tile "pt_operation" current)
  (mode_tile "pt_offset" (if (= mode "1") 0 1))
  (mode_tile "pt_file" (if (and (= source "1") (/= mode "3")) 0 1))
  (mode_tile "pick_file" (if (and (= source "1") (/= mode "3")) 0 1))
  (mode_tile "pt_format" (if (and (= source "1") (/= mode "3")) 0 1)))
(defun c:EXYZ () (setq *xyz:entry* "export") (c:XYZ))
(defun c:XYZEXPORTAR () (c:EXYZ))

;;; Pruebas integradas SIN modificar el dibujo. Ejecute XYZTEST.
(defun xyzt:test-check (label actual expected tol)
  (if (if tol (equal actual expected tol) (equal actual expected))
    (progn (setq *xyzt:test-ok* (1+ *xyzt:test-ok*)) (princ (strcat "\n  OK " label)))
    (progn (setq *xyzt:test-bad* (1+ *xyzt:test-bad*))
      (princ (strcat "\n  FALLO " label " obtenido=" (vl-prin1-to-string actual)
        " esperado=" (vl-prin1-to-string expected))))))
(defun c:XYZTEST (/ cfg classes stat poly z)
  (setq *xyzt:test-ok* 0 *xyzt:test-bad* 0)
  (xyzt:test-check "Ajuste cero numerico" (xyzt:setting-number "0") 0.0 1e-10)
  (xyzt:test-check "Ajuste con punto" (xyzt:setting-number "0.5") 0.5 1e-10)
  (xyzt:test-check "Ajuste con coma" (xyzt:setting-number "0,5") 0.5 1e-10)
  (xyzt:test-check "Ajuste negativo" (xyzt:setting-number "-8,5") -8.5 1e-10)
  (xyzt:test-check "Ajuste invalido" (xyzt:setting-number "abc") nil nil)
  (xyzt:test-check "Decimal punto" (xyzt:number "-12.500" ".") -12.5 1e-10)
  (xyzt:test-check "Decimal coma" (xyzt:number "-12,500" ",") -12.5 1e-10)
  (xyzt:test-check "Z cero" (xyzt:number "0" ".") 0.0 1e-10)
  (xyzt:test-check "Cientifico" (xyzt:number "1.25E+3" ".") 1250.0 1e-8)
  (xyzt:test-check "Signo mas" (xyzt:number "+.5" ".") 0.5 1e-10)
  (xyzt:test-check "Rechaza unidades" (xyzt:number "12m" ".") nil nil)
  (xyzt:test-check "Rechaza miles ambiguos" (xyzt:number "1,234.5" ".") nil nil)
  (xyzt:test-check "Rechaza vacio" (xyzt:number "" ".") nil nil)
  (xyzt:test-check "Rechaza exponente incompleto" (xyzt:number "1e-" ".") nil nil)
  (xyzt:test-check "WS mezclado" (xyzt:fields (strcat "1" (chr 9) "2  3") "WS") '("1" "2" "3") nil)
  (xyzt:test-check "CSV comillas" (xyzt:fields "1;\"a;b\";3" ";") '("1" "a;b" "3") nil)
  (xyzt:test-check "CSV campo vacio" (xyzt:fields "1;;3" ";") '("1" "" "3") nil)
  (xyzt:test-check "CSV comilla escapada" (xyzt:fields "1;\"a\"\"b\";3" ";") '("1" "a\"b" "3") nil)
  (xyzt:test-check "CSV comilla abierta" (xyzt:fields "1;\"2;3" ";") nil nil)
  (xyzt:test-check "Porcentaje 25" (xyzt:percent 250 1000) 25.0 1e-10)
  (xyzt:test-check "Porcentaje sin puntos" (xyzt:percent 0 0) 0.0 1e-10)
  (xyzt:test-check "Color hexadecimal" (xyzt:hex '(255 0 16)) "#FF0010" nil)
  (xyzt:test-check "Floor negativo" (xyzt:floor -0.1) -1 nil)
  (setq cfg (xyzt:defaults) cfg (xyzt:put 'xyfactor 1.0 cfg)
        cfg (xyzt:put 'zfactor -1.0 cfg) cfg (xyzt:put 'offset 2.0 cfg))
  (xyzt:test-check "Profundidad y nivel agua" (xyzt:line "574823.751 2110342.154 8.5" cfg "WS")
    '(574823.751 2110342.154 -6.5) 1e-8)
  (setq cfg (xyzt:put 'zfactor 1.0 cfg) cfg (xyzt:put 'offset 0.0 cfg))
  (xyzt:test-check "Cota negativa conservada" (caddr (xyzt:line "1 2 -8.5" cfg "WS")) -8.5 1e-10)
  (xyzt:test-check "Rechaza XY invalidos" (xyzt:line "error 2 3" cfg "WS") nil nil)
  (setq cfg (xyzt:put "cx" "2" cfg) cfg (xyzt:put "cy" "3" cfg) cfg (xyzt:put "cz" "4" cfg))
  (xyzt:test-check "ID XYZ" (xyzt:line "P01 1 2 3" cfg "WS") '(1.0 2.0 3.0) 1e-10)
  (setq classes '(("A" -2.0 -1.0 (0 0 0)) ("B" -1.0 0.0 (255 0 0))))
  (xyzt:test-check "Clase limite inferior" (xyzt:class-index -2.0 classes "0") 0 nil)
  (xyzt:test-check "Clase frontera interior" (xyzt:class-index -1.0 classes "0") 1 nil)
  (xyzt:test-check "Clase maximo incluido" (xyzt:class-index 0.0 classes "0") 1 nil)
  (xyzt:test-check "Fuera no satura" (xyzt:class-index 1.0 classes "0") nil nil)
  (xyzt:test-check "Saturacion explicita" (xyzt:class-index 1.0 classes "1") 1 nil)
  (setq poly '((0.0 0.0) (10.0 0.0) (10.0 10.0) (0.0 10.0)))
  (xyzt:test-check "Interior poligono" (xyzt:inside '(5 5 0) poly) T nil)
  (xyzt:test-check "Borde poligono" (xyzt:inside '(0 5 0) poly) T nil)
  (xyzt:test-check "Exterior poligono" (xyzt:inside '(11 5 0) poly) nil nil)
  (setq stat (xyzt:empty-stat))
  (foreach z '(1.0 2.0 3.0) (setq stat (xyzt:stat-add stat (list 0.0 0.0 z))))
  (xyzt:test-check "Media Welford" (cadr (car stat)) 2.0 1e-10)
  (xyzt:test-check "Desviacion Welford" (xyzt:std stat) 1.0 1e-10)
  (xyzt:test-check "Celda somero" (xyzt:grid-better '((0 0 -2) 2) '((0 0 -5) 1) 3) T nil)
  (xyzt:test-check "Celda profundo" (xyzt:grid-better '((0 0 -5) 2) '((0 0 -2) 1) 4) T nil)
  (xyzt:test-check "Celda conserva primero" (xyzt:grid-better '((0 0 -5) 2) '((0 0 -2) 1) 2) nil nil)
  (xyzt:test-check "Proceso invertir" (xyz:transform 8.5 0 0 nil 0 0) -8.5 1e-10)
  (xyzt:test-check "Proceso invertir cero" (xyz:transform 0.0 0 0 nil 0 0) 0.0 1e-10)
  (xyzt:test-check "Proceso offset" (xyz:transform -8.5 1 0.5 nil 0 0) -8.0 1e-10)
  (xyzt:test-check "Rango interior" (xyz:transform -5 2 0 '((-10 0 1) (0 10 2)) 0 0) -4 1e-10)
  (xyzt:test-check "Rango frontera unica" (xyz:transform 0 2 0 '((-10 0 1) (0 10 2)) 0 0) 2 1e-10)
  (xyzt:test-check "Rango exterior" (xyz:transform 11 2 0 '((-10 0 1) (0 10 2)) 0 0) 11 1e-10)
  (xyzt:test-check "Rango ultimo maximo" (xyz:transform 10 2 0 '((-10 0 1) (0 10 2)) 0 0) 12 1e-10)
  (xyzt:test-check "Eliminar Z cero" (xyz:transform 0 3 0 nil 0 0) nil nil)
  (xyzt:test-check "Conservar Z fuera" (xyz:transform -1 3 0 nil 0 0) -1 1e-10)
  (xyzt:test-check "Reemplazo solo columna Z" (xyz:replace-index '("P1" "100" "200" "-8.5" "arena") 3 "8.5")
    '("P1" "100" "200" "8.5" "arena") nil)
  (xyzt:test-check "Union de campos extra" (xyz:join '("P1" "100" "200" "8.5" "arena") ";") "P1;100;200;8.5;arena" nil)
  (xyzt:test-check "Rangos sin acumulacion" (xyz:transform -10 2 0 '((-10 0 1) (0 10 2)) 0 0) -9 1e-10)
  (xyzt:test-check "Etiqueta intervalo normal" (xyzt:class-label '("CLASE" -25.0 -24.5 (0 0 0))) "-25.00 a -24.50" nil)
  (xyzt:test-check "LAST de clases devuelve clase" (last '(("A" 1) ("B" 2))) '("B" 2) nil)
  (xyzt:test-check "LAST de poligono devuelve vertice" (last '((0 0) (1 0) (1 1))) '(1 1) nil)
  (princ (strcat "\nXYZTEST: " (itoa *xyzt:test-ok*) " correctas; " (itoa *xyzt:test-bad*)
    " fallidas. No verifica DCL, ActiveX, archivos ni entidades CAD.")) (princ))
(princ (strcat "\nXYZ-Tools " *xyzt:version* " cargado. Comandos XYZ / IXYZ / PZ / P-Z / IZ / OZ / ZM / XYZU | Ayuda XYZAYUDA | Pruebas XYZTEST"))
(princ)
